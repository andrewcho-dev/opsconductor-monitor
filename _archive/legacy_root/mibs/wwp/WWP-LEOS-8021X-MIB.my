-- This file was included in WWP MIB release 04-21-05-0007
--
-- WWP-LEOS-8021X-MIB.my
-- MIB generated by MG-SOFT Visual MIB Builder Version 6.0  Build 88
-- Sunday, August 28, 2005 at 19:49:14
--

    WWP-LEOS-8021X-MIB DEFINITIONS ::= BEGIN

        IMPORTS
            Integer32, Unsigned32, OBJECT-TYPE, MODULE-IDENTITY, NOTIFICATION-TYPE
                FROM SNMPv2-SMI
            DisplayString, TruthValue
                FROM SNMPv2-TC
            wwpModulesLeos
                FROM WWP-SMI
            dot1xPaeSystemAuthControl
                FROM IEEE8021-PAE-MIB;

        -- 1.3.6.1.4.1.6141.2.60.401
        wwpLeos8021xMibModule MODULE-IDENTITY
            LAST-UPDATED "201711150000Z"
            ORGANIZATION "Ciena Corp."
            CONTACT-INFO
                "   Mib Meister
                    7035 Ridge Road
                    Hanover, Maryland 21076
                    USA
                    Phone:  +1 800 921 1144
                    Email:  support@ciena.com"
            DESCRIPTION
                "The MIB module for WWP 802.1x supplicant and authenticator
                 information."
            REVISION    "201711150000Z"
            DESCRIPTION
                "Updated contact info."
            REVISION    "201710250000Z"
            DESCRIPTION
                "Added wwpLeos8021xSuppAlgorithmCipherSuiteTable, wwpLeos8021xSuppAlgorithmCipherSuiteEntry,
                wwpLeos8021xSuppAlgorithmCipherSuiteIndex, wwpLeos8021xSuppAlgorithmCipherSuiteName,
                wwpLeos8021xSuppAlgorithmCipherSuiteAdminState, wwpLeos8021xSuppAlgorithmCipherSuiteOperState,
                wwpLeos8021xSuppAlgorithmCipherSuitePriority
                Added wwpLeos8021xSuppAlgorithmEllipticCurveTable, wwpLeos8021xSuppAlgorithmEllipticCurveEntry,
                wwpLeos8021xSuppAlgorithmEllipticCurveIndex, wwpLeos8021xSuppAlgorithmEllipticCurveName,
                wwpLeos8021xSuppAlgorithmEllipticCurveAdminState, wwpLeos8021xSuppAlgorithmEllipticCurveOperState,
                wwpLeos8021xSuppAlgorithmEllipticCurvePriority"
            REVISION    "201707070000Z"
            DESCRIPTION
                "Added wwpLeos8021xSuppOCSPAdminState, wwpLeos8021xSuppCertificateName,
                wwpLeos8021xSuppMinimumTlsVersion, and wwpLeos8021xSuppPeerCertReauthAdminState
                to WwpLeos8021xSuppEntry."
            REVISION    "201510020000Z"
            DESCRIPTION
                "Added wwpLeos8021xSuppMutualAuthenticationOperState, and
                wwpLeos8021xSuppCheckCertificateTimeOperState."
            REVISION    "201509160000Z"
            DESCRIPTION
                "Added wwpLeos8021xSuppConfigChangeEvent,
                       wwpLeos8021xAuthConfigChangeEvent, and
                       wwpLeos8021xGlobalStateChangeEvent."
            REVISION    "201508100000Z"
            DESCRIPTION
                "Added wwpLeos8021xSuppEAPVersion and wwpLeos8021xSuppAdminState."
            REVISION    "201506250000Z"
            DESCRIPTION
                "Added wwpLeos8021xNotificationAuthenticationEvent,
                wwpLeos8021xSuppAuthenticationEvent, and
                wwpLeos8021xAuthAuthenticationEvent."
            REVISION    "201506220000Z"
            DESCRIPTION
                "Added wwpLeos8021xSuppSecret to the WwpLeos8021xSuppEntry
                 table."
            REVISION    "201506011800Z"
            DESCRIPTION
                "Obsoleted wwpLeos8021xSuppEAPMethod, and added
                wwpLeos8021xSuppEAPAllowedMethods,
                wwpLeos8021xSuppOperationalState,
                wwpLeos8021xSuppMutualAuthenticationAdminState,
                wwpLeos8021xSuppCheckCertificateTimeAdminState, and
                wwpLeos8021xSuppDeviceCertificateStatus.
                Also did formatting and description corrections."
            REVISION    "201304220000Z"
            DESCRIPTION
                "Miscellaneous spelling and description corrections."
            REVISION
                "201301150900Z"
            DESCRIPTION
                "Increased wwpLeos8021xSuppUserName to 32 characters.
                Increased wwpLeos8021xSuppPassword to 128 characters."
            REVISION
                "200508281935Z"
            DESCRIPTION
                "Initial version."
            ::= { wwpModulesLeos 401 }

--
-- Node definitions
--

        -- 1.3.6.1.4.1.6141.2.60.401.1
        wwpLeos8021xMIB OBJECT IDENTIFIER ::= { wwpLeos8021xMibModule 1 }

        -- 1.3.6.1.4.1.6141.2.60.401.1.1
        wwpLeos8021xConf OBJECT IDENTIFIER ::= { wwpLeos8021xMIB 1 }

        -- 1.3.6.1.4.1.6141.2.60.401.1.1.1
        wwpLeos8021xGroups OBJECT IDENTIFIER ::= { wwpLeos8021xConf 1 }

        -- 1.3.6.1.4.1.6141.2.60.401.1.1.2
        wwpLeos8021xCompls OBJECT IDENTIFIER ::= { wwpLeos8021xConf 2 }

        -- 1.3.6.1.4.1.6141.2.60.401.1.2
        wwpLeos8021xObjs OBJECT IDENTIFIER ::= { wwpLeos8021xMIB 2 }

        -- 1.3.6.1.4.1.6141.2.60.401.1.2.1
        wwpLeos8021xPortTable OBJECT-TYPE
            SYNTAX SEQUENCE OF WwpLeos8021xPortEntry
            MAX-ACCESS not-accessible
            STATUS current
            DESCRIPTION
                "Table with an entry for every port on the switch"
            ::= { wwpLeos8021xObjs 1 }

        -- 1.3.6.1.4.1.6141.2.60.401.1.2.1.1
        wwpLeos8021xPortEntry OBJECT-TYPE
            SYNTAX WwpLeos8021xPortEntry
            MAX-ACCESS not-accessible
            STATUS current
            DESCRIPTION
                "An entry (conceptual row) in the wwpLeos8021xPortTable."
            INDEX { wwpLeos8021xPort }
            ::= { wwpLeos8021xPortTable 1 }

        WwpLeos8021xPortEntry ::=
            SEQUENCE {
                wwpLeos8021xPort                    INTEGER,
                wwpLeos8021xRole                    INTEGER,
                wwpLeos8021xAuthPortStatsClear      INTEGER,
                wwpLeos8021xNotificationAuthenticationEvent INTEGER
             }

        -- 1.3.6.1.4.1.6141.2.60.401.1.2.1.1.1
        wwpLeos8021xPort OBJECT-TYPE
            SYNTAX INTEGER (1..1000)
            MAX-ACCESS read-only
            STATUS current
            DESCRIPTION
                "Switch Ethernet Port"
            ::= { wwpLeos8021xPortEntry 1 }

        -- 1.3.6.1.4.1.6141.2.60.401.1.2.1.1.2
        wwpLeos8021xRole OBJECT-TYPE
            SYNTAX INTEGER
                {
                none(1),
                supplicant(2),
                authenticator(3),
                both(4)
                }
            MAX-ACCESS read-write
            STATUS current
            DESCRIPTION
                "802.1x role of the Port."
            ::= { wwpLeos8021xPortEntry 2 }

        -- 1.3.6.1.4.1.6141.2.60.401.1.2.1.1.3
        wwpLeos8021xAuthPortStatsClear OBJECT-TYPE
            SYNTAX          TruthValue
            MAX-ACCESS      read-write
            STATUS          current
            DESCRIPTION
                "Setting this MIB object to 'true' clears the authenticator port statistics."
            ::= { wwpLeos8021xPortEntry 3 }

        -- 1.3.6.1.4.1.6141.2.60.401.1.2.1.1.4
        wwpLeos8021xNotificationAuthenticationEvent OBJECT-TYPE
            SYNTAX INTEGER
                 {
                 success(1),
                 failure(2),
                 timeout(3)
                 }
            MAX-ACCESS accessible-for-notify
            STATUS current
            DESCRIPTION
                 "This object identifies the type of authentication event being communicated
                 in the notification in which this object is located."
            ::= { wwpLeos8021xPortEntry 4 }


        -- 1.3.6.1.4.1.6141.2.60.401.1.3
        wwpLeos8021xEvents OBJECT IDENTIFIER ::= { wwpLeos8021xMIB 3 }

        -- 1.3.6.1.4.1.6141.2.60.401.1.3.0
        wwpLeos8021xEventsV2 OBJECT IDENTIFIER ::= { wwpLeos8021xEvents 0 }

--
-- Extension to dot1xSuppConfigTable Supplicant MIB
--

        -- 1.3.6.1.4.1.6141.2.60.401.1.2.2
        wwpLeos8021xSuppTable OBJECT-TYPE
            SYNTAX SEQUENCE OF WwpLeos8021xSuppEntry
            MAX-ACCESS not-accessible
            STATUS current
            DESCRIPTION
                "A table that contains the configuration objects for the
                 Supplicant PAE associated with each port.
                 An entry appears in this table for each port that may
                 authenticate itself when challenged by a remote system."
            ::= { wwpLeos8021xObjs 2 }

        -- 1.3.6.1.4.1.6141.2.60.401.1.2.2.1
        wwpLeos8021xSuppEntry OBJECT-TYPE
            SYNTAX WwpLeos8021xSuppEntry
            MAX-ACCESS not-accessible
            STATUS current
            DESCRIPTION
                "The configuration information for a Supplicant PAE."
            INDEX { wwpLeos8021xSuppPort }
            ::= { wwpLeos8021xSuppTable 1 }

        WwpLeos8021xSuppEntry ::=
            SEQUENCE {
                wwpLeos8021xSuppPort                            Integer32,
                wwpLeos8021xSuppUserName                        DisplayString,
                wwpLeos8021xSuppPassword                        DisplayString,
                wwpLeos8021xSuppPortStatsClear                  INTEGER,
                wwpLeos8021xSuppEAPMethod                       INTEGER,
                wwpLeos8021xSuppEAPAllowedMethods               BITS,
                wwpLeos8021xSuppOperationalState                INTEGER,
                wwpLeos8021xSuppMutualAuthenticationAdminState	INTEGER,
                wwpLeos8021xSuppCheckCertificateTimeAdminState	INTEGER,
                wwpLeos8021xSuppMutualAuthenticationOperState	INTEGER,
                wwpLeos8021xSuppCheckCertificateTimeOperState	INTEGER,
                wwpLeos8021xSuppDeviceCertificateStatus         INTEGER,
                wwpLeos8021xSuppSecret                          OCTET STRING,
                wwpLeos8021xSuppAdminState                      INTEGER,
                wwpLeos8021xSuppEAPVersion                      Integer32,
                wwpLeos8021xSuppOCSPAdminState                  INTEGER,
                wwpLeos8021xSuppCertificateName                 DisplayString,
                wwpLeos8021xSuppMinimumTlsVersion               INTEGER,
                wwpLeos8021xSuppPeerCertReauthAdminState        INTEGER
             }

        -- 1.3.6.1.4.1.6141.2.60.401.1.2.2.1.1
        wwpLeos8021xSuppPort OBJECT-TYPE
            SYNTAX          Integer32 (1..1000)
            MAX-ACCESS      read-only
            STATUS          current
            DESCRIPTION
                "The MIB object is used as an index in the table and specifies the port."
            ::= { wwpLeos8021xSuppEntry 1 }

        -- 1.3.6.1.4.1.6141.2.60.401.1.2.2.1.2
        wwpLeos8021xSuppUserName OBJECT-TYPE
            SYNTAX          DisplayString (SIZE(0..32))
            MAX-ACCESS      read-write
            STATUS          current
            DESCRIPTION
                "Username for authenticating this supplicant, also used as the 802.1x identity.
                 Setting this object to 0 resets the username."
            ::= { wwpLeos8021xSuppEntry 2 }

        -- 1.3.6.1.4.1.6141.2.60.401.1.2.2.1.3
        wwpLeos8021xSuppPassword OBJECT-TYPE
            SYNTAX          DisplayString (SIZE(0..128))
            MAX-ACCESS      read-write
            STATUS          current
            DESCRIPTION
                "The password used with wwpLeos8021xSuppUserName for EAP-MD5 authentication.
                 Doing a get on this object always returns a zero length string for security reasons."
            ::= { wwpLeos8021xSuppEntry 3 }

        -- 1.3.6.1.4.1.6141.2.60.401.1.2.2.1.5
        wwpLeos8021xSuppPortStatsClear OBJECT-TYPE
            SYNTAX          TruthValue
            MAX-ACCESS      read-write
            STATUS          current
            DESCRIPTION
                "Setting this MIB object to 'true' clears the supplicant port statistics."
            ::= { wwpLeos8021xSuppEntry 5 }

        -- 1.3.6.1.4.1.6141.2.60.401.1.2.2.1.10
        wwpLeos8021xSuppEAPMethod OBJECT-TYPE
            SYNTAX          INTEGER {
                                    eapMd5(1)
            }
            MAX-ACCESS      read-write
            STATUS          obsolete
            DESCRIPTION
                "Obsolete. Use wwpLeos8021xSuppEAPAllowedMethods instead."
            ::= { wwpLeos8021xSuppEntry 10 }

        -- 1.3.6.1.4.1.6141.2.60.401.1.2.2.1.11
        wwpLeos8021xSuppEAPAllowedMethods OBJECT-TYPE
            SYNTAX      BITS {
                                eapMd5(0),
                                eapTls(1)
                        }
            MAX-ACCESS      read-write
            STATUS          current
            DESCRIPTION
                "Extensible Authentication Protocol methods allowed for this supplicant."
            ::= { wwpLeos8021xSuppEntry 11 }

        -- 1.3.6.1.4.1.6141.2.60.401.1.2.2.1.12
        wwpLeos8021xSuppOperationalState OBJECT-TYPE
            SYNTAX      INTEGER {
                                disabled(1),
                                enabled(2)
                        }
            MAX-ACCESS      read-only
            STATUS          current
            DESCRIPTION
                "Returns the operational state of this supplicant."
            ::= { wwpLeos8021xSuppEntry 12 }

        -- 1.3.6.1.4.1.6141.2.60.401.1.2.2.1.13
        wwpLeos8021xSuppMutualAuthenticationAdminState OBJECT-TYPE
            SYNTAX      INTEGER {
                                disabled(1),
                                enabled(2)
                        }
            MAX-ACCESS      read-write
            STATUS          current
            DESCRIPTION
                "Administratively enables/disables authentication of the
                 server by the supplicant. Applies to EAP-TLS."
            ::= { wwpLeos8021xSuppEntry 13 }

        -- 1.3.6.1.4.1.6141.2.60.401.1.2.2.1.14
        wwpLeos8021xSuppCheckCertificateTimeAdminState OBJECT-TYPE
            SYNTAX      INTEGER {
                                disabled(1),
                                enabled(2)
                        }
            MAX-ACCESS      read-write
            STATUS          current
            DESCRIPTION
                "Administratively enables/disables checking of the server's
                 certificate timestamp when doing mutual authentication.
                 Applies to EAP-TLS."
            ::= { wwpLeos8021xSuppEntry 14 }

        -- 1.3.6.1.4.1.6141.2.60.401.1.2.2.1.15
        wwpLeos8021xSuppMutualAuthenticationOperState OBJECT-TYPE
            SYNTAX      INTEGER {
                                disabled(1),
                                enabled(2)
                        }
            MAX-ACCESS      read-only
            STATUS          current
            DESCRIPTION
                "Returns the operative state of mutual authentication checking.
                 Applies to EAP-TLS."
            ::= { wwpLeos8021xSuppEntry 15 }

        -- 1.3.6.1.4.1.6141.2.60.401.1.2.2.1.16
        wwpLeos8021xSuppCheckCertificateTimeOperState OBJECT-TYPE
            SYNTAX      INTEGER {
                                disabled(1),
                                enabled(2)
                        }
            MAX-ACCESS      read-only
            STATUS          current
            DESCRIPTION
                "Returns the operative state of certificate time stamp checking when
                 doing mutual authentication. Applies to EAP-TLS."
            ::= { wwpLeos8021xSuppEntry 16 }

        -- 1.3.6.1.4.1.6141.2.60.401.1.2.2.1.17
        wwpLeos8021xSuppDeviceCertificateStatus OBJECT-TYPE
            SYNTAX      INTEGER {
                                valid(1),
                                invalid(2),
                                notPresent(3)
                        }
            MAX-ACCESS      read-only
            STATUS          current
            DESCRIPTION
                "Returns the state of the supplicant device certificate.
                 Applies to EAP-TLS."
            ::= { wwpLeos8021xSuppEntry 17 }

        -- 1.3.6.1.4.1.6141.2.60.401.1.2.2.1.18
       wwpLeos8021xSuppSecret OBJECT-TYPE
            SYNTAX          OCTET STRING(SIZE(0..259))
            MAX-ACCESS      read-write
            STATUS          current
            DESCRIPTION
                 "Sets the pre-encrypted secret that shall be used along with the
                  username specified by wwpLeos8021xSuppUserName to gain access
                  on a port. A get returns the encrypted secret for the supplicant."
            ::= { wwpLeos8021xSuppEntry 18}

        -- 1.3.6.1.4.1.6141.2.60.401.1.2.2.1.19
       wwpLeos8021xSuppAdminState OBJECT-TYPE
            SYNTAX       INTEGER {
                                 disabled(1),
                                 enabled(2)
                         }
            MAX-ACCESS   read-write
            STATUS       current
            DESCRIPTION
                 "This object is used to specify the user administrative state
                  of the supplicant port."
            ::= { wwpLeos8021xSuppEntry 19 }

        -- 1.3.6.1.4.1.6141.2.60.401.1.2.2.1.20
       wwpLeos8021xSuppEAPVersion OBJECT-TYPE
            SYNTAX       Integer32 (1..2)
            MAX-ACCESS   read-write
            STATUS       current
            DESCRIPTION
                 "This object is used to specify the EAPoL version of the supplicant
                  port."
            ::= { wwpLeos8021xSuppEntry 20 }

        -- 1.3.6.1.4.1.6141.2.60.401.1.2.2.1.21
       wwpLeos8021xSuppOCSPAdminState OBJECT-TYPE
            SYNTAX      INTEGER {
                                disabled(1),
                                enabled(2)
                        }
            MAX-ACCESS      read-write
            STATUS          current
            DESCRIPTION
                "Administratively enables/disables OCSP checking of the server's
                 certificate when doing mutual authentication.
                 Applies to EAP-TLS."
            ::= { wwpLeos8021xSuppEntry 21 }

        -- 1.3.6.1.4.1.6141.2.60.401.1.2.2.1.22
       wwpLeos8021xSuppCertificateName OBJECT-TYPE
            SYNTAX          DisplayString (SIZE(0..32))
            MAX-ACCESS      read-write
            STATUS          current
            DESCRIPTION
                "Name of the certificate to be used for authenticating this supplicant.
                 Applies to EAP-TLS."
            ::= { wwpLeos8021xSuppEntry 22 }

        -- 1.3.6.1.4.1.6141.2.60.401.1.2.2.1.23
        wwpLeos8021xSuppMinimumTlsVersion OBJECT-TYPE
            SYNTAX      INTEGER {
                                version1dot0(1),
                                version1dot1(2),
                                version1dot2(3)
                        }
            MAX-ACCESS      read-write
            STATUS          current
            DESCRIPTION
                "This object is used to specify the minimum TLS version that can be
                 used by the supplicant port.
                 Applies to EAP-TLS."
            ::= { wwpLeos8021xSuppEntry 23 }

        -- 1.3.6.1.4.1.6141.2.60.401.1.2.2.1.24
       wwpLeos8021xSuppPeerCertReauthAdminState OBJECT-TYPE
            SYNTAX      INTEGER {
                                disabled(1),
                                enabled(2)
                        }
            MAX-ACCESS      read-write
            STATUS          current
            DESCRIPTION
                "Administratively enables/disables peer certificate reauthentication
                 on this supplicant.
                 Applies to EAP-TLS."
            ::= { wwpLeos8021xSuppEntry 24 }

        -- 1.3.6.1.4.1.6141.2.60.401.1.2.3
        wwpLeos8021xGlobalAttrs OBJECT IDENTIFIER ::= { wwpLeos8021xObjs 3 }

        -- 1.3.6.1.4.1.6141.2.60.401.1.2.3.1
        wwpLeos8021xAuthStatsClear OBJECT-TYPE
            SYNTAX          TruthValue
            MAX-ACCESS      read-write
            STATUS          current
            DESCRIPTION
                "Setting this MIB object to 'true' clears the authenticator global statistics."
            ::= { wwpLeos8021xGlobalAttrs 1 }

        -- 1.3.6.1.4.1.6141.2.60.401.1.2.3.2
        wwpLeos8021xSuppStatsClear OBJECT-TYPE
            SYNTAX          TruthValue
            MAX-ACCESS      read-write
            STATUS          current
            DESCRIPTION
                "Setting this MIB object to 'true' clears the supplicant global statistics."
            ::= { wwpLeos8021xGlobalAttrs 2 }

        -- 1.3.6.1.4.1.6141.2.60.401.1.2.4
        wwpLeos8021xSuppAlgorithmCipherSuiteTable OBJECT-TYPE
            SYNTAX SEQUENCE OF WwpLeos8021xSuppAlgorithmCipherSuiteEntry
            MAX-ACCESS not-accessible
            STATUS current
            DESCRIPTION
                "A table that contains the configuration objects for the
                 supplicant algorithm cipher suite.
                 This table is shared by every port that may
                 authenticate itself when challenged by a remote system."
            ::= { wwpLeos8021xObjs 4 }

        -- 1.3.6.1.4.1.6141.2.60.401.1.2.4.1
        wwpLeos8021xSuppAlgorithmCipherSuiteEntry OBJECT-TYPE
            SYNTAX WwpLeos8021xSuppAlgorithmCipherSuiteEntry
            MAX-ACCESS not-accessible
            STATUS current
            DESCRIPTION
                "The configuration information for a cipher suite."
            INDEX { wwpLeos8021xSuppAlgorithmCipherSuiteIndex }
            ::= { wwpLeos8021xSuppAlgorithmCipherSuiteTable 1 }

        WwpLeos8021xSuppAlgorithmCipherSuiteEntry ::= SEQUENCE {
                wwpLeos8021xSuppAlgorithmCipherSuiteIndex              Unsigned32,
                wwpLeos8021xSuppAlgorithmCipherSuiteName               DisplayString,
                wwpLeos8021xSuppAlgorithmCipherSuiteAdminState         INTEGER,
                wwpLeos8021xSuppAlgorithmCipherSuiteOperState          INTEGER,
                wwpLeos8021xSuppAlgorithmCipherSuitePriority           Unsigned32
             }

        -- 1.3.6.1.4.1.6141.2.60.401.1.2.4.1.1
         wwpLeos8021xSuppAlgorithmCipherSuiteIndex OBJECT-TYPE
            SYNTAX          Unsigned32 (1..65535)
            MAX-ACCESS      not-accessible
            STATUS          current
            DESCRIPTION
                "An arbitrary index into the table identifying a unique algorithm as
                 identified by the value of wwpLeosSSHServerEncryptionAlgorithmName object"
            ::= { wwpLeos8021xSuppAlgorithmCipherSuiteEntry 1 }

        -- 1.3.6.1.4.1.6141.2.60.401.1.2.4.1.2
        wwpLeos8021xSuppAlgorithmCipherSuiteName OBJECT-TYPE
            SYNTAX          DisplayString
            MAX-ACCESS      read-only
            STATUS          current
            DESCRIPTION
                "Name of the algorithm as used when negotiating
                 the encryption algorithm with clients."
            ::= { wwpLeos8021xSuppAlgorithmCipherSuiteEntry 2 }

        -- 1.3.6.1.4.1.6141.2.60.401.1.2.4.1.3
        wwpLeos8021xSuppAlgorithmCipherSuiteAdminState OBJECT-TYPE
            SYNTAX          INTEGER {
                               disabled(1),
                               enabled(2)
            }
            MAX-ACCESS      read-write
            STATUS          current
            DESCRIPTION
                "The administrative state of the cipher suite, indicating whether the
                 administrative settings are set to allow the inclusion of the
                 specified cipher suite in the algorithm negotiation process.
                 Such inclusion or exclusion of the cipher suite is indicated by the
                 corresponding value of wwpLeos8021xSuppAlgorithmCipherSuiteOperState."
            ::= { wwpLeos8021xSuppAlgorithmCipherSuiteEntry 3 }

        -- 1.3.6.1.4.1.6141.2.60.401.1.2.4.1.4
        wwpLeos8021xSuppAlgorithmCipherSuiteOperState OBJECT-TYPE
            SYNTAX          INTEGER {
                               disabled(1),
                               enabled(2)
            }
            MAX-ACCESS      read-only
            STATUS          current
            DESCRIPTION
                "The operational state of the cipher suite, indicating whether the
                 specified cipher suite will be included in the algorithm
                 negotiation process. The operational state is determined based on
                 the corresponding value of wwpLeos8021xSuppAlgorithmCipherSuiteAdminState
                 as well as other system attributes which may limit the allowable
                 cipher suites that may be used."
            ::= { wwpLeos8021xSuppAlgorithmCipherSuiteEntry 4 }

        -- 1.3.6.1.4.1.6141.2.60.401.1.2.4.1.5
         wwpLeos8021xSuppAlgorithmCipherSuitePriority OBJECT-TYPE
            SYNTAX          Unsigned32 (1..65535)
            MAX-ACCESS      read-write
            STATUS          current
            DESCRIPTION
                "The priority, or importance, of the specified cipher suite amongst
                 the other cipher suites in this table. Value 1 is highest priority.
                 During the algorithm negotiation, the protocol will consider
                 all operationally enabled cipher suites in order of priority, as part
                 of the algorithm negotiation process.  When the priority of one
                 cipher suite is set to a new value, it will necessarily cause the
                 priority of other cipher suites to adjust in order to make room
                 for the new set priority of the cipher suite."
            ::= { wwpLeos8021xSuppAlgorithmCipherSuiteEntry 5}

        -- 1.3.6.1.4.1.6141.2.60.401.1.2.5
        wwpLeos8021xSuppAlgorithmEllipticCurveTable OBJECT-TYPE
            SYNTAX SEQUENCE OF WwpLeos8021xSuppAlgorithmEllipticCurveEntry
            MAX-ACCESS not-accessible
            STATUS current
            DESCRIPTION
                "A table that contains the configuration objects for the
                 supplicant elliptic curve.
                 This table is shared by every port that may
                 authenticate itself when challenged by a remote system."
            ::= { wwpLeos8021xObjs 5 }

        -- 1.3.6.1.4.1.6141.2.60.401.1.2.5.1
        wwpLeos8021xSuppAlgorithmEllipticCurveEntry OBJECT-TYPE
            SYNTAX WwpLeos8021xSuppAlgorithmEllipticCurveEntry
            MAX-ACCESS not-accessible
            STATUS current
            DESCRIPTION
                "The configuration information for an elliptic curve."
            INDEX { wwpLeos8021xSuppAlgorithmEllipticCurveIndex }
            ::= { wwpLeos8021xSuppAlgorithmEllipticCurveTable 1 }

        WwpLeos8021xSuppAlgorithmEllipticCurveEntry ::= SEQUENCE {
                wwpLeos8021xSuppAlgorithmEllipticCurveIndex              Unsigned32,
                wwpLeos8021xSuppAlgorithmEllipticCurveName               DisplayString,
                wwpLeos8021xSuppAlgorithmEllipticCurveAdminState         INTEGER,
                wwpLeos8021xSuppAlgorithmEllipticCurveOperState          INTEGER,
                wwpLeos8021xSuppAlgorithmEllipticCurvePriority           Unsigned32
             }

        -- 1.3.6.1.4.1.6141.2.60.401.1.2.5.1.1
         wwpLeos8021xSuppAlgorithmEllipticCurveIndex OBJECT-TYPE
            SYNTAX          Unsigned32 (1..65535)
            MAX-ACCESS      not-accessible
            STATUS          current
            DESCRIPTION
                "An arbitrary index into the table identifying a unique elliptic curve as
                 identified by the value of wwpLeos8021xSuppAlgorithmEllipticCurveName object."
            ::= { wwpLeos8021xSuppAlgorithmEllipticCurveEntry 1 }

        -- 1.3.6.1.4.1.6141.2.60.401.1.2.5.1.2
        wwpLeos8021xSuppAlgorithmEllipticCurveName OBJECT-TYPE
            SYNTAX          DisplayString
            MAX-ACCESS      read-only
            STATUS          current
            DESCRIPTION
                "Name of the elliptic curve as used when negotiating
                 the encryption algorithm with clients."
            ::= { wwpLeos8021xSuppAlgorithmEllipticCurveEntry 2 }

        -- 1.3.6.1.4.1.6141.2.60.401.1.2.5.1.3
        wwpLeos8021xSuppAlgorithmEllipticCurveAdminState OBJECT-TYPE
            SYNTAX          INTEGER {
                               disabled(1),
                               enabled(2)
            }
            MAX-ACCESS      read-write
            STATUS          current
            DESCRIPTION
                "The administrative state of the elliptic curve, indicating whether the
                 administrative settings are set to allow the inclusion of the
                 specified elliptic curve in the algorithm negotiation process.
                 Such inclusion or exclusion of the elliptic curve is indicated by the
                 corresponding value of wwpLeos8021xSuppAlgorithmEllipticCurveOperState."
            ::= { wwpLeos8021xSuppAlgorithmEllipticCurveEntry 3 }

        -- 1.3.6.1.4.1.6141.2.60.401.1.2.5.1.4
        wwpLeos8021xSuppAlgorithmEllipticCurveOperState OBJECT-TYPE
            SYNTAX          INTEGER {
                               disabled(1),
                               enabled(2)
            }
            MAX-ACCESS      read-only
            STATUS          current
            DESCRIPTION
                "The operational state of the elliptic curve, indicating whether the
                 specified elliptic curve will be included in the algorithm
                 negotiation process. The operational state is determined based on
                 the corresponding value of wwpLeos8021xSuppAlgorithmEllipticCurveAdminState
                 as well as other system attributes which may limit the allowable
                 algorithms that may be used."
            ::= { wwpLeos8021xSuppAlgorithmEllipticCurveEntry 4 }

        -- 1.3.6.1.4.1.6141.2.60.401.1.2.5.1.5
         wwpLeos8021xSuppAlgorithmEllipticCurvePriority OBJECT-TYPE
            SYNTAX          Unsigned32 (1..65535)
            MAX-ACCESS      read-write
            STATUS          current
            DESCRIPTION
                "The priority, or importance, of the specified elliptic curve amongst
                 the other elliptic curves in this table.  Value 1 is highest priority.
                 During the algorithm negotiation, the protocol will consider
                 all operationally enabled elliptic curves in order of priority, as part
                 of the algorithm negotiation process.  When the priority of one
                 elliptic curve is set to a new value, it will necessarily cause the
                 priority of other elliptic curves to adjust in order to make room
                 for the new set priority of the elliptic curve."
            ::= { wwpLeos8021xSuppAlgorithmEllipticCurveEntry 5}

--
-- Notifications
--

        -- 1.3.6.1.4.1.6141.2.60.401.1.4
        wwpLeos8021xMIBNotificationPrefix  OBJECT IDENTIFIER ::= { wwpLeos8021xMIB 4 }

        -- 1.3.6.1.4.1.6141.2.60.401.1.4.0
        wwpLeos8021xMIBNotification        OBJECT IDENTIFIER ::= { wwpLeos8021xMIBNotificationPrefix 0 }

        -- 1.3.6.1.4.1.6141.2.60.401.1.4.0.1
        wwpLeos8021xSuppAuthenticationEvent NOTIFICATION-TYPE
            OBJECTS {
                        wwpLeos8021xPort,
                        wwpLeos8021xNotificationAuthenticationEvent
                    }
            STATUS     current
            DESCRIPTION     "This notification is generated when a supplicant authentication event,
                             as identified by the value of wwpLeos8021xNotificationAuthenticationEvent
                             has occurred on the port identified by wwpLeos8021xPort."
            ::= { wwpLeos8021xMIBNotification 1 }

        -- 1.3.6.1.4.1.6141.2.60.401.1.4.0.2
        wwpLeos8021xAuthAuthenticationEvent NOTIFICATION-TYPE
            OBJECTS {
                      wwpLeos8021xPort,
                      wwpLeos8021xNotificationAuthenticationEvent
                     }
            STATUS     current
            DESCRIPTION     "This notification is generated when a authenticator authentication event,
                             as identified by the value of wwpLeos8021xNotificationAuthenticationEvent
                             has occurred on the port identified by wwpLeos8021xPort."
            ::= { wwpLeos8021xMIBNotification 2 }

        -- 1.3.6.1.4.1.6141.2.60.401.1.4.0.3
        wwpLeos8021xGlobalStateChangeEvent NOTIFICATION-TYPE
            OBJECTS {
                      dot1xPaeSystemAuthControl
                    }
            STATUS     current
            DESCRIPTION     "This notification is generated when the dot1x global state is
                             changed."
            ::= { wwpLeos8021xMIBNotification 3 }

        -- 1.3.6.1.4.1.6141.2.60.401.1.4.0.4
        wwpLeos8021xAuthConfigChangeEvent NOTIFICATION-TYPE
            OBJECTS {
                      wwpLeos8021xPort
                    }
            STATUS     current
            DESCRIPTION     "This notification is generated when a configuration change is made
                             in a dot1x authentication port."
            ::= { wwpLeos8021xMIBNotification 4 }

        -- 1.3.6.1.4.1.6141.2.60.401.1.4.0.5
        wwpLeos8021xSuppConfigChangeEvent NOTIFICATION-TYPE
            OBJECTS {
                      wwpLeos8021xPort
                    }
            STATUS     current
            DESCRIPTION     "This notification is generated when a configuration change is made
                             in a dot1x supplicant port."
            ::= { wwpLeos8021xMIBNotification 5 }
    END

--
-- WWP-LEOS-8021X-MIB.my
--
