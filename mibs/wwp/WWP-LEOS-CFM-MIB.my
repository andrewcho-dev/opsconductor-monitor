-- This file was included in WWP MIB release 04-21-05-0007

 --
 -- WWP-LEOS-CFM-MIB.my
 --     

 WWP-LEOS-CFM-MIB DEFINITIONS ::= BEGIN

 IMPORTS                
   TimeTicks, Integer32, Unsigned32, Gauge32, Counter32, Counter64, OBJECT-TYPE, MODULE-IDENTITY, NOTIFICATION-TYPE                       
        FROM SNMPv2-SMI                 
   DisplayString, MacAddress, TEXTUAL-CONVENTION, RowStatus , TruthValue                
        FROM SNMPv2-TC
   sysName
        FROM RFC1213-MIB                                                        
   wwpModulesLeos           
        FROM WWP-SMI
   cienaGlobalSeverity, cienaGlobalMacAddress
        FROM  CIENA-GLOBAL-MIB;
        
 wwpLeosCfmMIB MODULE-IDENTITY
             LAST-UPDATED "201908080000Z"
             ORGANIZATION "Ciena Corp."
             CONTACT-INFO
                "Mib Meister
                 7035 Ridge Road
                 Hanover, Maryland 21076
                 USA
                 Phone:  +1 800 921 1144
                 Email:  support@ciena.com"
             DESCRIPTION
                "Connectivity Fault Management (CFM) MIB for configuration and monitoring CFM"

             REVISION "202111150000Z"
             DESCRIPTION
                "Added wwpLeosCfmExtSynLossSessionPriority and wwpLeosCfmExtSynLossSessionTestId varbinds to
                 wwpLeosCfmExtSynLossSessionNearFaultTrap, wwpLeosCfmExtSynLossSessionFarFaultTrap,
                 wwpLeosCfmExtSynLossSessionNearFaultClearTrap and wwpLeosCfmExtSynLossSessionFarFaultClearTrap traps."

             REVISION "201908080000Z"
             DESCRIPTION
                "Added wwpLeosCfmExtDelaySessionForwardJitterProfile and wwpLeosCfmExtDelaySessionBackwardJitterProfile 
                 objects to wwpLeosCfmExtDelaySessionTable."

             REVISION "201905290000Z"
             DESCRIPTION
                "Added wwpLeosCfmExtDelaySessionSdDelayClearThreshold, wwpLeosCfmExtDelaySessionSdDelaySetThreshold and
                 wwpLeosCfmExtDelaySessionSdJitterClearThreshold, wwpLeosCfmExtDelaySessionSdJitterSetThreshold to
                 wwpLeosCfmExtDelaySessionTable.
                 Added wwpLeosCfmExtDelaySessionHistorySignalDegradeStatus and wwpLeosCfmExtDelaySessionHistorySignalDegradeSuspect to
                 wwpLeosCfmExtDelaySessionHistoryTable.
                 Added wwpLeosCfmExtDelaySessionSignalDegradeFaultSetTrap and wwpLeosCfmExtDelaySessionSignalDegradeFaultClearTrap
                 to wwpLeosCfmNotifMIBNotification."

             REVISION "201905290000Z"
             DESCRIPTION
                "Below MIB tables are marked as obsolete. The functionality of the table is shifted to corresponding wwpLeosCfmExt* 
                 table -
                 - wwpLeosCfmLinkTraceMsgTable, wwpLeosCfmLinkTraceMsgReplyTable
                 - wwpLeosCfmLoopbackMsgTable
                 - wwpLeosCfmMEPTable
                 - wwpLeosCfmDelayMsgTable
                 - wwpLeosCfmFrameLossMsgTable"

             REVISION "201905280000Z"
             DESCRIPTION
                "wwpLeosCfmMipEntry marked as obsolete.The functionality of the table is shifted to wwpLeosCfmExtMipEntry."

             REVISION "201904260000Z"
             DESCRIPTION
                "Added wwpLeosCfmServiceYProtectionMonitoringState object to wwpLeosCfmServiceTable."
          
             REVISION "201901140000Z"
             DESCRIPTION
                "Added cienaGlobalSeverity,cienaGlobalMacAddress objects to wwpLeosCfmBlockOppositeMEPSetTrap, wwpLeosCfmBlockOppositeMEPClearTrap,
                 wwpLeosCfmExtSynLossSessionNearFaultTrap, wwpLeosCfmExtSynLossSessionFarFaultTrap, wwpLeosCfmExtSynLossSessionNearFaultClearTrap,
                 wwpLeosCfmExtSynLossSessionFarFaultClearTrap, wwpLeosCfmExtDelaySessionAvgDelayFaultSetTrap, wwpLeosCfmExtDelaySessionAvgDelayFaultClearTrap,
                 wwpLeosCfmExtDelaySessionAvgJitterFaultSetTrap, wwpLeosCfmExtDelaySessionAvgJitterFaultClearTrap, wwpLeosCfmExtDelaySessionMaxDelayFaultSetTrap,
                 wwpLeosCfmExtDelaySessionMaxDelayFaultClearTrap, wwpLeosCfmExtDelaySessionMaxJitterFaultSetTrap, wwpLeosCfmExtDelaySessionMaxJitterFaultClearTrap,
                 wwpLeosCfmExtFrameLossSessionFrameLossNearFaultSetTrap, wwpLeosCfmExtFrameLossSessionFrameLossNearFaultClearTrap, wwpLeosCfmExtFrameLossSessionFrameLossFarFaultSetTrap,
                 wwpLeosCfmExtFrameLossSessionFrameLossFarFaultClearTrap, wwpLeosCfmFrameLossSessionBadSequenceTrap, wwpLeosCfmServiceCsfFaultSetTrap, wwpLeosCfmServiceCsfFaultClearTrap,
                 wwpLeosCfmExtSynLossSessionSignalDegradeFaultSetTrap, wwpLeosCfmExtSynLossSessionSignalDegradeFaultClearTrap NOTIFICATION-TYPE macros."

             REVISION "201812240000Z"
             DESCRIPTION
                "Added cienaGlobalSeverity,cienaGlobalMacAddress objects to wwpLeosCfmExtFaultTrapSet,wwpLeosCfmExtFaultTrapClear NOTIFICATION-TYPE macro."
 
             REVISION "201810090000Z"
             DESCRIPTION
                "Modified value range and description of objects wwpLeosCfmExtSynLossSessionSdSetThreshold
                 and wwpLeosCfmExtSynLossSessionSdClearThreshold in wwpLeosCfmExtSynLossSessionTable."
 
             REVISION "201810080000Z"
             DESCRIPTION
                "Added new object wwpLeosCfmExtDelaySessionCosMode in wwpLeosCfmExtDelaySessionTable."
 
             REVISION "201810010000Z"
             DESCRIPTION
                "Added new object wwpLeosCfmExtMEPLagMemberPortId to support creation of MEP on LAG member port."
             
             REVISION "201809180000Z"
             DESCRIPTION
                "Marked the status of wwpLeosCfmServiceDMMInterval as obsolete."

             REVISION "201801120000Z"
             DESCRIPTION
                "Updated range for object wwpLeosCfmServiceAlarmTime."

             REVISION "201712050000Z"
             DESCRIPTION
                "Expanded the value range of objects - wwpLeosCfmExtDelayMsgDelayThreshold, wwpLeosCfmExtDelayMsgJitterThreshold,
                 wwpLeosCfmExtDelayMsgMaxDelayThreshold, wwpLeosCfmExtDelayMsgMaxJitterThreshold."

             REVISION "201709190000Z"
             DESCRIPTION
                "Removed Unnecessary bracket symbols from the DESCRIPTION clauses of wwpLeosCfmExtDelaySessionIterations, wwpLeosCfmExtFrameLossSessionIterations
                 and wwpLeosCfmExtFrameLossSessionIterations."

             REVISION "201706120000Z"
             DESCRIPTION
                "Added new objects as a part of Y.1731 one-way delay measurements feature support.
                 Added wwpLeosCfmExtMEPDMMForwardMinDelay, wwpLeosCfmExtMEPDMMForwardAveDelay, wwpLeosCfmExtMEPDMMForwardMaxDelay, 
                       wwpLeosCfmExtMEPDMMBackwardMinDelay, wwpLeosCfmExtMEPDMMBackwardAveDelay, wwpLeosCfmExtMEPDMMBackwardMaxDelay
                       in wwpLeosCfmExtMEPTable.
                 Added wwpLeosCfmExtMEPLastStatsDMMForwardMinDelay, wwpLeosCfmExtMEPLastStatsDMMForwardAveDelay, wwpLeosCfmExtMEPLastStatsDMMForwardMaxDelay,
                       wwpLeosCfmExtMEPLastStatsDMMBackwardMinDelay, wwpLeosCfmExtMEPLastStatsDMMBackwardAveDelay, wwpLeosCfmExtMEPLastStatsDMMBackwardMaxDelay
                       in wwpLeosCfmExtMEPLastStatsTable Table.
                 Added wwpLeosCfmExtMEPDelayHistoryForwardMinDelay, wwpLeosCfmExtMEPDelayHistoryForwardAveDelay, wwpLeosCfmExtMEPDelayHistoryForwardMaxDelay,
                       wwpLeosCfmExtMEPDelayHistoryBackwardMinDelay, wwpLeosCfmExtMEPDelayHistoryBackwardAveDelay, wwpLeosCfmExtMEPDelayHistoryBackwardMaxDelay 
                       in wwpLeosCfmExtMEPDelayHistoryTable table.
                 Added wwpLeosCfmExtDelaySessionForwardMinDelay, wwpLeosCfmExtDelaySessionForwardAveDelay, wwpLeosCfmExtDelaySessionForwardMaxDelay,
                       wwpLeosCfmExtDelaySessionBackwardMinDelay, wwpLeosCfmExtDelaySessionBackwardAveDelay, wwpLeosCfmExtDelaySessionBackwardMaxDelay,
                       wwpLeosCfmExtDelaySessionConfigTimestampType in wwpLeosCfmExtDelaySessionTable.
                 Added wwpLeosCfmExtDelaySessionHistoryForwardMinDelay, wwpLeosCfmExtDelaySessionHistoryForwardAveDelay, wwpLeosCfmExtDelaySessionHistoryForwardMaxDelay,
                       wwpLeosCfmExtDelaySessionHistoryBackwardMinDelay, wwpLeosCfmExtDelaySessionHistoryBackwardAveDelay,  wwpLeosCfmExtDelaySessionHistoryBackwardMaxDelay
                       in wwpLeosCfmExtDelaySessionHistoryTable.
                 Added wwpLeosCfmExt2DelayResponderTable which is an extension of wwpLeosCfmExtDelayResponderTable by adding wwpLeosCfmExt2DelayResponderTestId (index), wwpLeosCfmExt2DelayResponderTimestampType."

             REVISION "201706020000Z"
             DESCRIPTION
                "Added new object in global table wwpLeosCfmGlobalSlmResponderAging."

             REVISION    "201705050000Z"
             DESCRIPTION
             "Added wwpLeosCfmExtMEPSLMTwoWayFrameLoss, wwpLeosCfmExtMEPSLMTwoWayFrameLossRatio to wwpLeosCfmExtMEPTable.
              Added wwpLeosCfmExtSynLossSessionTwoWayFrameLoss, wwpLeosCfmExtSynLossSessionTwoWayFrameLossRatio to wwpLeosCfmExtSynLossSessionTable.
              Added wwpLeosCfmExtSynLossSessionHistoryTwoWayFrameLoss and wwpLeosCfmExtSynLossSessionHistoryTwoWayFrameLossRatio to wwpLeosCfmExtSynLossSessionHistoryTable."

             REVISION    "201704060000Z"
             DESCRIPTION
             "Added wwpLeosCfmExtMEPSignalDegradeMonitoringStatus and wwpLeosCfmExtMEPSignalDegradeTriggerMode to wwpLeosCfmExtMEPTable.
              Added wwpLeosCfmExtSynLossSessionSdSetThreshold and wwpLeosCfmExtSynLossSessionSdClearThreshold to wwpLeosCfmExtSynLossSessionTable. 
              Added wwpLeosCfmExtSynLossSessionHistorySignalDegradeStatus and wwpLeosCfmExtSynLossSessionHistorySignalDegradeSuspect to 
              wwpLeosCfmExtSynLossSessionHistoryTable.
              Added wwpLeosCfmExtSynLossSessionSignalDegradeFaultSetTrap and wwpLeosCfmExtSynLossSessionSignalDegradeFaultClearTrap 
              to wwpLeosCfmNotifMIBNotification."

             REVISION    "201611300000Z"
             DESCRIPTION
             "Added CSF Feature related config, operdata and statistics related fields in CFM Global, Service, Mep Tables." 

             REVISION    "201609120000Z"
             DESCRIPTION
             "Added wwpLeosCfmExtMEPDelayBinHistoryTable and wwpLeosCfmExtDelaySessionBinHistoryTable Tables." 

             REVISION    "201606270000Z"
             DESCRIPTION
             "Added suspect attribute in Delay Measurement and Synthetic Loss Measurement Tables." 

             REVISION    "201606160000Z"
             DESCRIPTION
             "Added wwpLeosCfmExtMEPSLMFrameDeliveryRatio, wwpLeosCfmExtSynLossSessionFrameDeliveryRatio and wwpLeosCfmExtSynLossSessionHistoryFrameDeliveryRatio" 

             REVISION    "201606060000Z"
             DESCRIPTION
             "Added Oneway Dmm Jitter Counters and One way Dmm Jitter Bins" 

             REVISION    "201605190000Z"
             DESCRIPTION
             "Added wwpLeosCfmRemoteMEPCvid" 

             REVISION    "201509240000Z"
             DESCRIPTION
             "Added wwpLeosCfmExtDelaySessionDelayProfile and wwpLeosCfmExtDelaySessionJitterProfile." 

             REVISION    "201508280000Z"
             DESCRIPTION
             "Added wwpLeosCfmExtDelaySessionConfigAccelerated, wwpLeosCfmExtFrameLossSessionConfigAccelerated, and 
              wwpLeosCfmExtSynLossSessionConfigAccelerated. Modify DESCRIPTION for wwpLeosCfmExtDelaySessionAccelerated, 
              wwpLeosCfmExtFrameLossSessionAccelerated, and wwpLeosCfmExtSynLossSessionAccelerated."     

             REVISION    "201506120000Z"
             DESCRIPTION
             "Added Synthetic Loss Measurement responder table. Added accelerated OID to Synthetic Loss Table"     

             REVISION    "201503160000Z"
             DESCRIPTION
             "Added delay measurement bins profile and counters."    

             REVISION "201502230000Z"
             DESCRIPTION
             "Added Tx and Rx frame counters for frame loss and synthetic loss tests."

             REVISION    "201409160000Z"
             DESCRIPTION
             "Added frame loss ratio near and far variables to both frame loss and synthetic loss tests."
             
             REVISION    "201409090000Z"
             DESCRIPTION
             "Added missing SLM objects wwpLeosCfmExtMEPLastStatsSLMPriority, wwpLeosCfmExtMEPLastStatsSLMTxmt, wwpLeosCfmExtMEPLastStatsSLMReceived,
              wwpLeosCfmExtMEPLastStatsSLMNearLoss and wwpLeosCfmExtMEPLastStatsSLMFarLoss to wwpLeosCfmExtMEPLastStatsTable."

             REVISION    "201402150000Z"
             DESCRIPTION
             "Added new set and clear traps for delay, frame loss and synthetic loss to monitor faults when the threshold value exceeds or returns
              to normal."
                
             REVISION    "201309170000Z"
             DESCRIPTION
             "Added missing SLM objects wwpLeosCfmExtMEPStatsInvalidSLMReceived, wwpLeosCfmExtMEPStatsInvalidSLRReceived to
              wwpLeosCfmExtMEPStatsTable table. And, also added wwpLeosCfmExtSynLossSessionHistoryRemoteMacAddr to the table
              wwpLeosCfmExtSynLossSessionHistoryTable."

             REVISION    "201308070000Z"
             DESCRIPTION
                "Updated range for object wwpLeosCfmExtDelaySessionFrameSize."
 
             REVISION    "201307220000Z"
             DESCRIPTION
                "Miscellaneous description corrections."

             REVISION    "201306260000Z"
             DESCRIPTION
                "Added new objects to support delay and frame-loss history accelerate state."

             REVISION    "201304220000Z"
             DESCRIPTION
                "Miscellaneous spelling and description corrections."

             REVISION "201304020000Z"
             DESCRIPTION
                "Added new object in global table wwpLeosCfmGlobalVsAutoMepCreate."

             REVISION "201304010000Z"
             DESCRIPTION
                "Added new tables wwpLeosCfmExtDelaySessionTable, wwpLeosCfmExtDelaySessionHistoryTable, wwpLeosCfmExtDelayResponderTable,
                 wwpLeosCfmExtFrameLossSessionTable, wwpLeosCfmExtFrameLossSessionHistoryTable and wwpLeosCfmExtFrameLossResponderTable.
                 Added new columns wwpLeosCfmExtOamPortHwY1731DmmSupported and wwpLeosCfmExtOamPortHwY1731LmmSupported to the table wwpLeosCfmExtOamPortTable."

             REVISION "201302110000Z"
             DESCRIPTION
                "Removed column wwpLeosCfmExtSynLossSessionData from the object wwpLeosCfmExtSynLossSessionEntry."

             REVISION "201301150000Z"
             DESCRIPTION
                "Added new objects wwpLeosCfmTotalTxSLM, wwpLeosCfmTotalTxSLR, wwpLeosCFMTotalRxSLM and wwpLeosCfmTotalRxSLR to wwpLeosCfmGlobalStats Table.
                 Added new column wwpLeosCfmExtSynLossSessionHistoryIteration to the wwpLeosCfmExtSynLossSessionHistoryTable.
                 Added new objects wwpLeosCfmServiceTotalTxSLM, wwpLeosCfmServiceTotalTxSLR, wwpLeosCfmServiceTotalRxSLM and wwpLeosCfmServiceTotalRxSLR to the 
                 table wwpLeosCfmServiceStatisticsTable." 

             REVISION "201211210000Z"
             DESCRIPTION
                "Added new tables wwpLeosCfmExtSynLossSessionTable and wwpLeosCfmExtSynLossSessionHistoryTable.
                 Added new objects wwpLeosCfmExtMEPStatsSLMTxmt, wwpLeosCfmExtMEPStatsSLMReceived, wwpLeosCfmExtMEPStatsSLRTxmt, 
                 wwpLeosCfmExtMEPStatsSLRReceived, wwpLeosCfmExtMEPStatsSLRTimeout under WwpLeosCfmExtMEPStatsEntry.
                 Added new objects which indicate Notification Traps wwpLeosCfmExtSynLossSessionNearFaultTrap, wwpLeosCfmExtSynLossSessionFarFaultTrap
                 under wwpLeosCfmNotifMIBNotification."

             REVISION "201204110000Z"
             DESCRIPTION
                "Expanded value ranges for Delay fields to allow setting of the 'default' value (-1 for threshold,
                 0 for msgcount). Merged 6.x changes back into 4.x MIB to make them identical. Cleaned up history section
                 to conform to standard - REVISION comes before DESCRIPTION"

             REVISION "201202030000Z"
             DESCRIPTION
                "Added new objects wwpLeosCfmServiceAccelerated,wwpLeosCfmRemoteMEPAccelerated and wwpLeosCfmExtMEPAccelerated.
                 Added a new table for query for port OAM capability."

             REVISION "201107260000Z"
             DESCRIPTION
                "Added new objects wwpLeosCfmRemoteMEPServiceClear,wwpLeosCfmRemoteMEPServiceStatisticsClear"

             REVISION "201105310000Z"
             DESCRIPTION
                "Deprecated objects wwpLeosCfmLBMDefaultCount,wwpLeosCfmLBMDefaultInterval,wwpLeosCfmLBMDefaultTimeout,
                 wwpLeosCfmFrameClassifierMode under wwpLeosCfmGlobal.
                 Added objects wwpLeosCfmGlobalLBMDefaultCount,wwpLeosCfmGlobalLBMDefaultInterval,wwpLeosCfmGlobalLBMDefaultTimeout,
                 wwpLeosCfmGlobalFrameClassifierMode under wwpLeosCfmGlobal.
                 Deprecated wwpLeosCfmServiceDefaultMEPType,wwpLeosCfmServiceMAID,wwpLeosCfmServiceMdIndex,wwpLeosCfmServiceMaintAssocNameType,
                 wwpLeosCfmServiceMaintAssocName under WwpLeosCfmServiceEntry.
                 Added wwpLeosCfmServiceY1731,wwpLeosCfmServiceCCMTxState,wwpLeosCfmServiceRMEPAging,wwpLeosCfmServiceMulticastDa,
                 wwpLeosCfmServiceChargedAgainstGlobalFrameBudget,wwpLeosCfmServiceCfmDefaultMEPType,wwpLeosCfmServiceCfmMAID,
                 wwpLeosCfmServiceCfmMdIndex,wwpLeosCfmServiceCfmMaintAssocNameType,wwpLeosCfmServiceCfmMaintAssocName,
                 wwpLeosCfmServiceCfmControlModuleFrameBudget under WwpLeosCfmService.
                 Added wwpLeosCfmLinkTraceMsgServiceName,wwpLeosCfmLinkTraceMsgSubPortName,wwpLeosCfmLinkTraceMsgVsIndex,
                 wwpLeosCfmLinkTraceMsgTotalTxLtm,wwpLeosCfmLinkTraceMsgTotalRxLtr under wwpLeosCfmLinkTraceMsg.
                 Added wwpLeosCfmLinkTraceMsgReplyIngressMacAddr,wwpLeosCfmLinkTraceMsgReplyEgressMacAddr under 
                 WwpLeosCfmLinkTraceMsgReplyEntry.
                 Added wwpLeosCfmMEPDMMMinDelay,wwpLeosCfmMEPDMMMaxDelay,wwpLeosCfmMEPDMMMinJitter,wwpLeosCfmMEPDMMMaxJitter,
                 wwpLeosCfmMEPServiceName,wwpLeosCfmMEPSubPortName,wwpLeosCfmMEPVsPbtName,wwpLeosCfmMEPLogicalPortName,
                 wwpLeosCfmMEPSubPortIndex,wwpLeosCfmMEPEncapsulation,wwpLeosCfmMEPLeadPortBayIndex,wwpLeosCfmMEPLeadPortShelfIndex,
                 wwpLeosCfmMEPLeadPortModuleIndex,wwpLeosCfmMEPPBTBvid,wwpLeosCfmMEPPBTEtype,wwpLeosCfmMEPNumLbmTxmt, wwpLeosCfmMEPNumLbmReceived,
                 wwpLeosCfmMEPNumLoopbackRepliesReceived,wwpLeosCfmMEPNumLTRepliesTxmt, wwpLeosCfmMEPNumLTRepliesReceived,
                 wwpLeosCfmMEPNumUnexpectedLTRepliesReceived,wwpLeosCfmMEPNumCCMReceived under wwpLeosCfmMEPEntry.
                 Deprecated wwpLeosCfmRemoteMEPHoldState under wwpLeosCfmRemoteMEP.
                 Added wwpLeosCfmRemoteMEPMinDelay,wwpLeosCfmRemoteMEPMaxDelay,wwpLeosCfmRemoteMEPMinJitter,wwpLeosCfmRemoteMEPMaxJitter,
                 wwpLeosCfmRemoteCfmMEPHoldState,wwpLeosCfmRemoteMEPSubPortName,wwpLeosCfmRemoteMEPServiceName ,wwpLeosCfmRemoteMEPBayIndex,
                 wwpLeosCfmRemoteMEPShelfIndex,wwpLeosCfmRemoteMEPModuleIndex ,wwpLeosCfmRemoteMEPPreviousBayIndex,
                 wwpLeosCfmRemoteMEPPreviousShelfIndex ,wwpLeosCfmRemoteMEPPreviousModuleIndex,wwpLeosCfmRemoteMEPLastPortStatus,
                 wwpLeosCfmRemoteMEPLastInterfaceStatus,wwpLeosCfmRemoteMEPLastSeqNum, wwpLeosCfmRemoteMEPCCMSeqErrors,
                 wwpLeosCfmRemoteMEPCCMLevel,wwpLeosCfmRemoteMEPDeleteAll under wwpLeosCfmRemoteMEPEntry.
                 Deprecated the table wwpLeosCfmPortStackTable .
                 Added wwpLeosCfmServiceVsPbtName under  WwpLeosCfmServiceFaultEntry.
                 Added wwpLeosCfmDelayMsgMaxDelayThreshold, wwpLeosCfmDelayMsgMaxJitterThreshold under wwpLeosCfmDelayMsgEntry.
                 Added wwpLeosCfmExtMEPDMMMinDelay,wwpLeosCfmExtMEPDMMMaxDelay,wwpLeosCfmExtMEPDMMMinJitter,wwpLeosCfmExtMEPDMMMaxJitter 
                 under wwpLeosCfmExtMEPEntry.
                 Added wwpLeosCfmExtMEPLastStatsDMMMinDelay,wwpLeosCfmExtMEPLastStatsDMMMaxDelay,wwpLeosCfmExtMEPLastStatsDMMMinJitter,
                 wwpLeosCfmExtMEPLastStatsDMMMaxJitter under wwpLeosCfmExtMEPLastStatsEntry.
                 Added wwpLeosCfmExtDelayMsgMaxDelayThreshold,wwpLeosCfmExtDelayMsgMaxJitterThreshold under wwpLeosCfmExtDelayMsgEntry.
                 Added new tables wwpLeosCfmGlobalFrameBudgetTable,wwpLeosCfmServiceFrameBudgetTable,wwpLeosCfmExtPortStackTable,
                 wwpLeosCfmExtMEPDelayHistoryTable,wwpLeosTceCfmMipTable,wwpLeosTceCfmMipCCMDbTable,wwpLeosTceCfmLoopbackMsgTable,
                 wwpLeosTceCfmPortStackTable,wwpLeosTceCfmMEPTable,wwpLeosTceCfmDelayMsgTable,wwpLeosTceCfmFrameLossMsgTable.
                 Added new notifications wwpLeosCfmFaultTrapSet,wwpLeosCfmFaultTrapClear,wwpLeosCfmDmmTrap,wwpLeosCfmLmmTrap." 
                  
            REVISION "201101310000Z"
            DESCRIPTION
                "Deprecated object wwpLeosCfmPbtFaultTrap."

            REVISION "201007150000Z"
            DESCRIPTION
               "Added wwpLeosCfmLBMDefaultCount, wwpLeosCfmLBMDefaultInterval, wwpLeosCfmLBMDefaultTimeout,
               and wwpLeosCfmFrameClassifierMode under wwpLeosCfmGlobal.
               Added wwpLeosCfmTotalRxDropBlockedOppositeMep under wwpLeosCfmGlobalStats.
               Added wwpLeosCfmServiceMAID, wwpLeosCfmServiceMdIndex, wwpLeosCfmServiceMaintAssocNameType,
               and wwpLeosCfmServiceMaintAssocName under WwpLeosCfmServiceEntry.
               Added wwpLeosCfmLoopbackMsgDefaultInterval and wwpLeosCfmLoopbackMsgDefaultTimeout
               under WwpLeosCfmLoopbackMsgEntry.
               Added wwpLeosCfmMaintenanceDomainMdFormat, wwpLeosCfmMaintenanceDomainMdName, and
               wwpLeosCfmMaintenanceDomainStatus under WwpLeosCfmMaintenanceDomainEntry.
               Added wwpLeosCfmExtLoopbackMsgInterval, wwpLeosCfmExtLoopbackMsgTimeout,
               and wwpLeosCfmExtLoopbackMsgLoss under WwpLeosCfmExtLoopbackMsgEntry.
               Added wwpLeosCfmExtMEPBlockOppositeFaultCurrent, wwpLeosCfmExtMEPBlockOppositeFaultThreshold,
               and wwpLeosCfmExtMEPBlockOppositeFaultTime under WwpLeosCfmExtMEPEntry.
               Added wwpLeosCfmExtMEPStatsInvalidBlockedOppositeMep under WwpLeosCfmExtMEPStatsEntry.
               Added wwpLeosCfmBlockOppositeMEPSetTrap and wwpLeosCfmBlockOppositeMEPClearTrap under
               wwpLeosCfmNotifMIBNotification."
 
            REVISION "200911160000Z"
            DESCRIPTION
               "Added wwpLeosCfmExtMEPLMMMissingSequence under wwpLeosCfmExtMEPEntry"

            REVISION "200909041700Z"
            DESCRIPTION 
               "Added wwpLeosCfmExtMipTable under wwpLeosCfmExtMIBObj"

            REVISION "200908061900Z"
            DESCRIPTION 
               "Added wwpLeosCfmRemoteMEPBadSequence under wwpLeosCfmRemoteMEPEntry"

            REVISION "200907301900Z"
            DESCRIPTION
               "Added wwpLeosCfmL2LoopDetectState, wwpLeosCfmDot1adStrict, wwpLeosCfmMipLevelEnforcement and wwpLeosCfmMipCcmDbState
               under wwpLeosGlobal
               Added wwpLeosCfmServiceDefaultMEPType under wwpLeosCfmServiceEntry.
               Added wwpLeosCfmRemoteMEPCCMComment under wwpLeosCfmRemoteMEPEntry.
               Added wwpLeosCfmExtMEPLMMBadSequence and wwpLeosCfmExtMEPCCMComment under wwpLeosCfmExtMEPEntry.
               Added wwpLeosCfmExtMEPLastStatsFrameLossBadSequence under wwpLeosCfmExtMEPLastStatsEntry.
               Added wwpLeosCfmExtFrameLossMsgSeqThreshold under wwpLeosCfmExtFrameLossMsgEntry.
               Added wwpLeosCfmBadSequenceFaultTrap under wwpLeosCfmNotifMIBNotification."

            REVISION    "200811141700Z" 
            DESCRIPTION
               "Added wwpLeosCfmExtInterfaceStackTable under wwpLeosCfmExtMIBObj
               Added wwpLeosCfmExtMepCfmServiceName, wwpLeosCfmExtMepInterfaceName, wwpLeosCfmExtMepServiceInstanceName,
               wwpLeosCfmExtMepLogicalPortName to wwpLeosCfmExtMepEntryTable
               Added wwpLeosCfmFaultTrapSet and wwpLeosCfmFaultTrapClear Notifications"

            REVISION    "200810231700Z"
            DESCRIPTION
               "Added wwpLeosCfmExtLoopback, wwpLeosCfmExtMEP, wwpLeosCfmExtLinkTrace, 
               wwpLeosCfmExtDelay and wwpLeosCfmExtFrameLoss tables under wwpLeosCfmExtMIBObj.
               Added wwpLeosCfmServiceRemoteMepDiscovery under wwpLeosCfmServiceTableEntry.
               Added wwpLeosCfmRemoteMEPHoldState and wwpLeosCfmRemoteMEPRowStatus."
     
            REVISION    "200710241700Z"  
            DESCRIPTION
               "changed the properties on the WwpLeosCfmServiceFaultTable to read
               only"  

            REVISION    "200604181700Z"
            DESCRIPTION
               "Initial creation."
            ::= { wwpModulesLeos 35 }

 --
 -- Node definitions
 --        
 --wwpLeosCfmMIBObjects            
 wwpLeosCfmMIBObjects OBJECT IDENTIFIER ::= { wwpLeosCfmMIB 1 }

 wwpLeosCfmGlobal OBJECT IDENTIFIER ::= { wwpLeosCfmMIBObjects 1 }  
 
 wwpLeosCfmService OBJECT IDENTIFIER ::= { wwpLeosCfmMIBObjects 2 }

 wwpLeosCfmMIP OBJECT IDENTIFIER ::= { wwpLeosCfmMIBObjects 3 }        

 wwpLeosCfmLinkTrace OBJECT IDENTIFIER ::= { wwpLeosCfmMIBObjects 4 }        

 wwpLeosCfmLoopback OBJECT IDENTIFIER ::= { wwpLeosCfmMIBObjects 5 }

 wwpLeosCfmMaintenance OBJECT IDENTIFIER ::= { wwpLeosCfmMIBObjects 6 }

 wwpLeosCfmMEP OBJECT IDENTIFIER ::= { wwpLeosCfmMIBObjects 7 }                                                         

 wwpLeosCfmRemoteMEP OBJECT IDENTIFIER ::= { wwpLeosCfmMIBObjects 8 }

 wwpLeosCfmStack OBJECT IDENTIFIER ::= { wwpLeosCfmMIBObjects 9 }

 wwpLeosCfmMipCCMDb OBJECT IDENTIFIER ::= { wwpLeosCfmMIBObjects 10 }  

 wwpLeosCfmFaultNotif OBJECT IDENTIFIER ::= { wwpLeosCfmMIBObjects 11 }  

 wwpLeosCfmDelay OBJECT IDENTIFIER ::= { wwpLeosCfmMIBObjects 12 }  

 wwpLeosCfmFrameLoss OBJECT IDENTIFIER ::= { wwpLeosCfmMIBObjects 13 } 

 wwpLeosCfmRemoteMEPCCMLoss OBJECT IDENTIFIER ::= { wwpLeosCfmMIBObjects 14 }   
              
 wwpLeosCfmExtStack OBJECT IDENTIFIER ::= { wwpLeosCfmMIBObjects 15 }
 
 wwpLeosCfmServiceFrameBudget	OBJECT IDENTIFIER ::= { wwpLeosCfmMIBObjects 16}

 wwpLeosCfmExtMIBObj OBJECT IDENTIFIER ::= { wwpLeosCfmMIBObjects 21 }
 
 --wwpLeosCfmGlobal
 wwpLeosCfmGlobalFrameBudget OBJECT IDENTIFIER ::= { wwpLeosCfmGlobal 24 }
 
 wwpLeosCfmGlobalStats OBJECT IDENTIFIER ::= {wwpLeosCfmGlobal 25}    
 
 --wwpLeosCfmGlobalStats
 wwpLeosCfmGlobalCCMStats OBJECT IDENTIFIER ::= { wwpLeosCfmGlobalStats 26}

 wwpLeosCfmGlobalLoopbackStats OBJECT IDENTIFIER ::= { wwpLeosCfmGlobalStats 27}

 wwpLeosCfmGlobalLinkTraceStats OBJECT IDENTIFIER ::= { wwpLeosCfmGlobalStats 28}

 wwpLeosCfmGlobalDelayMeasurementStats OBJECT IDENTIFIER ::= { wwpLeosCfmGlobalStats 29 }

 wwpLeosCfmGlobalLossMeasurementStats OBJECT IDENTIFIER ::= { wwpLeosCfmGlobalStats 30}   
 
 wwpLeosCfmGlobalSLMMeasurementStats OBJECT IDENTIFIER ::=  { wwpLeosCfmGlobalStats 31}
 
 wwpLeosCfmGlobalCSFStats OBJECT IDENTIFIER ::= { wwpLeosCfmGlobalStats 32}
 
 --wwpLeosCfmExtMIBObj
 wwpLeosCfmExtLoopback OBJECT IDENTIFIER ::= { wwpLeosCfmExtMIBObj 3 }

 wwpLeosCfmExtMEP OBJECT IDENTIFIER ::= { wwpLeosCfmExtMIBObj 7 } 

 wwpLeosCfmExtLinkTrace OBJECT IDENTIFIER ::= { wwpLeosCfmExtMIBObj 8 }

 wwpLeosCfmExtDelay OBJECT IDENTIFIER ::= { wwpLeosCfmExtMIBObj 12 }

 wwpLeosCfmExtFrameLoss OBJECT IDENTIFIER ::= { wwpLeosCfmExtMIBObj 13 }

 wwpLeosCfmExtInterfaceStack OBJECT IDENTIFIER ::= { wwpLeosCfmExtMIBObj 14 }  

 wwpLeosCfmExtMIP OBJECT IDENTIFIER ::= { wwpLeosCfmExtMIBObj 15 }

 wwpLeosCfmExtInterfaceMIP OBJECT IDENTIFIER ::= { wwpLeosCfmExtMIBObj 16 }

 wwpLeosCfmExtOamPort OBJECT IDENTIFIER ::= { wwpLeosCfmExtMIBObj 17 } 
 
 wwpLeosCfmExtSynLoss OBJECT IDENTIFIER ::= { wwpLeosCfmExtMIBObj 18 }    

 wwpLeosCfmDmmDelayProfile OBJECT IDENTIFIER ::= { wwpLeosCfmMIBObjects 22 }
  --
  -- Delay Profile Bin table
  -- 
  wwpLeosCfmDelayProfileTable OBJECT-TYPE
     SYNTAX     SEQUENCE OF WwpLeosCfmDelayProfileEntry
     MAX-ACCESS not-accessible
     STATUS     current
     DESCRIPTION
            "The (conceptual) table listing the configuration 
            parameters for the DelayProfile."
     ::= { wwpLeosCfmDmmDelayProfile 1 }

 wwpLeosCfmDelayProfileEntry OBJECT-TYPE
     SYNTAX      WwpLeosCfmDelayProfileEntry
     MAX-ACCESS  not-accessible
     STATUS      current
     DESCRIPTION
           "An entry (conceptual row) in the wwpLeosCfmDelayProfileTable."
     INDEX {wwpLeosCfmDelayProfileIndex}
     ::= { wwpLeosCfmDelayProfileTable 1 }

 WwpLeosCfmDelayProfileEntry ::=  SEQUENCE {
     wwpLeosCfmDelayProfileIndex                    Unsigned32,
     wwpLeosCfmDelayProfileName                     DisplayString,
     wwpLeosCfmDelayThresholdBin1                   Unsigned32,
     wwpLeosCfmDelayThresholdBin2                   Unsigned32,
     wwpLeosCfmDelayThresholdBin3                   Unsigned32,
     wwpLeosCfmDelayThresholdBin4                   Unsigned32,
     wwpLeosCfmDelayThresholdBin5                   Unsigned32,
     wwpLeosCfmDelayThresholdBin6                   Unsigned32,
     wwpLeosCfmDelayThresholdBin7                   Unsigned32,
     wwpLeosCfmDelayThresholdBin8                   Unsigned32,
     wwpLeosCfmDelayThresholdBin9                   Unsigned32,
     wwpLeosCfmDelayThresholdBin10                  Unsigned32,
     wwpLeosCfmDelayProfileRowStatus                RowStatus
 }

wwpLeosCfmDelayProfileIndex OBJECT-TYPE
     SYNTAX       Unsigned32 (1..4096)
     MAX-ACCESS   not-accessible
     STATUS       current
     DESCRIPTION
             "This object specifies the profile Index."
     ::= { wwpLeosCfmDelayProfileEntry 1 }
wwpLeosCfmDelayProfileName OBJECT-TYPE
        SYNTAX       DisplayString (SIZE(1..45))
        MAX-ACCESS   read-create
        STATUS       current
        DESCRIPTION
        "Denotes a delay profile Name."
        ::= { wwpLeosCfmDelayProfileEntry 2 }
wwpLeosCfmDelayThresholdBin1 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 3 }
wwpLeosCfmDelayThresholdBin2 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 4 }
wwpLeosCfmDelayThresholdBin3 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 5 }
wwpLeosCfmDelayThresholdBin4 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 6 }
wwpLeosCfmDelayThresholdBin5 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 7 }
wwpLeosCfmDelayThresholdBin6 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 8 }
wwpLeosCfmDelayThresholdBin7 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 9 }
wwpLeosCfmDelayThresholdBin8 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 10 }
wwpLeosCfmDelayThresholdBin9 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 11 }
wwpLeosCfmDelayThresholdBin10 OBJECT-TYPE
        SYNTAX                  Unsigned32 (0..2147483647)
        MAX-ACCESS              read-create
        STATUS                  current
        DESCRIPTION
                        "The threshold for the Delay Measurement bin, specified
                        in microseconds.  A value of 0 disables the bin. "
        ::= { wwpLeosCfmDelayProfileEntry 12 }
wwpLeosCfmDelayProfileRowStatus OBJECT-TYPE
     SYNTAX       RowStatus
     MAX-ACCESS   read-create
     STATUS       current
     DESCRIPTION
             "Used to manage the creation and deletion of the conceptual rows in this table.
             To create a row in this table, set this object to 'createAndGo'. 
             To delete a row in this table, set this to 'destroy'. "
     ::= { wwpLeosCfmDelayProfileEntry 13 }

 wwpLeosCfmDmmJitterProfile OBJECT IDENTIFIER ::= { wwpLeosCfmMIBObjects 23 }
  --
  -- Jitter Profile Bin table
  -- 
 wwpLeosCfmJitterProfileTable OBJECT-TYPE
     SYNTAX     SEQUENCE OF WwpLeosCfmJitterProfileEntry
     MAX-ACCESS not-accessible
     STATUS     current
     DESCRIPTION
            "The (conceptual) table listing the configuration 
            parameters for the JitterProfile."
     ::= { wwpLeosCfmDmmJitterProfile 1 }

 wwpLeosCfmJitterProfileEntry OBJECT-TYPE
     SYNTAX      WwpLeosCfmJitterProfileEntry
     MAX-ACCESS  not-accessible
     STATUS      current
     DESCRIPTION
           "An entry (conceptual row) in the wwpLeosCfmJitterProfileTable."
     INDEX {wwpLeosCfmJitterProfileIndex}
     ::= { wwpLeosCfmJitterProfileTable 1 }

 WwpLeosCfmJitterProfileEntry ::=  SEQUENCE {
     wwpLeosCfmJitterProfileIndex                    Unsigned32,
     wwpLeosCfmJitterProfileName                     DisplayString,
     wwpLeosCfmJitterThresholdBin1                   Unsigned32,
     wwpLeosCfmJitterThresholdBin2                   Unsigned32,
     wwpLeosCfmJitterThresholdBin3                   Unsigned32,
     wwpLeosCfmJitterThresholdBin4                   Unsigned32,
     wwpLeosCfmJitterThresholdBin5                   Unsigned32,
     wwpLeosCfmJitterThresholdBin6                   Unsigned32,
     wwpLeosCfmJitterThresholdBin7                   Unsigned32,
     wwpLeosCfmJitterThresholdBin8                   Unsigned32,
     wwpLeosCfmJitterThresholdBin9                   Unsigned32,
     wwpLeosCfmJitterThresholdBin10                  Unsigned32,
     wwpLeosCfmJitterProfileRowStatus                RowStatus
 }

wwpLeosCfmJitterProfileIndex OBJECT-TYPE
     SYNTAX       Unsigned32 (1..4096)
     MAX-ACCESS   not-accessible
     STATUS       current
     DESCRIPTION
             "This object specifies the profile Index."
     ::= { wwpLeosCfmJitterProfileEntry 1 }
wwpLeosCfmJitterProfileName OBJECT-TYPE
        SYNTAX       DisplayString (SIZE(1..45))
        MAX-ACCESS   read-create
        STATUS       current
        DESCRIPTION
        "Denotes a jitter profile Name."
        ::= { wwpLeosCfmJitterProfileEntry 2 }
wwpLeosCfmJitterThresholdBin1 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 3 }
wwpLeosCfmJitterThresholdBin2 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 4 }
wwpLeosCfmJitterThresholdBin3 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 5 }
wwpLeosCfmJitterThresholdBin4 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 6 }
wwpLeosCfmJitterThresholdBin5 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 7 }
wwpLeosCfmJitterThresholdBin6 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 8 }
wwpLeosCfmJitterThresholdBin7 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 9 }
wwpLeosCfmJitterThresholdBin8 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 10 }
wwpLeosCfmJitterThresholdBin9 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 11 }
wwpLeosCfmJitterThresholdBin10 OBJECT-TYPE
        SYNTAX                  Unsigned32 (0..2147483647)
        MAX-ACCESS              read-create
        STATUS                  current
        DESCRIPTION
                        "The threshold for the Jitter Measurement bin, specified
                        in microseconds.  A value of 0 disables the bin. "
        ::= { wwpLeosCfmJitterProfileEntry 12 }
wwpLeosCfmJitterProfileRowStatus OBJECT-TYPE
     SYNTAX       RowStatus
     MAX-ACCESS   read-create
     STATUS       current
     DESCRIPTION
             "Used to manage the creation and deletion of the conceptual rows in this table.
             To create a row in this table, set this object to 'createAndGo'. 
             To delete a row in this table, set this to 'destroy'. "
     ::= { wwpLeosCfmJitterProfileEntry 13 }

 
 -- Notifications 
  
 wwpLeosCfmNotifMIBNotificationPrefix  OBJECT IDENTIFIER ::= { wwpLeosCfmMIB 2 } 
 
 wwpLeosCfmNotifMIBNotification       OBJECT IDENTIFIER ::=  { wwpLeosCfmNotifMIBNotificationPrefix 0 }
 
  -- Conformance information  
 wwpLeosCfmMIBConformance OBJECT IDENTIFIER ::= { wwpLeosCfmMIB 3 } 
 wwpLeosCfmMIBCompliances OBJECT IDENTIFIER ::= { wwpLeosCfmMIBConformance 1 }                
 wwpLeosCfmMIBGroups      OBJECT IDENTIFIER ::= { wwpLeosCfmMIBConformance 2 }
              
 CfmMAID ::= TEXTUAL-CONVENTION
    DISPLAY-HINT "1x:"
    STATUS      current
    DESCRIPTION 
             "Binary data representing the md name and ma name."
    SYNTAX      OCTET STRING(SIZE(1..48))

 CfmDisplayString ::= TEXTUAL-CONVENTION
    DISPLAY-HINT "1x:"
    STATUS      current
    DESCRIPTION
            "Represents the cfm display string."
    SYNTAX      OCTET STRING (SIZE(1..2))
    
 EthType ::= TEXTUAL-CONVENTION
    DISPLAY-HINT "1x:"
    STATUS      current
    DESCRIPTION
        "Represents the ethernet type."
    SYNTAX      OCTET STRING (SIZE(1..2))
    
 SendState ::= TEXTUAL-CONVENTION
    STATUS      current
    DESCRIPTION
        "Represents the action for the row. 
         Send (1): the message with the corresponding parameters
         is to be sent to the Target host
         Clear (2): Clears the counters of the particular entry
         Cancel (3)"
    SYNTAX      INTEGER {
                   send(1),
                   clear(2),
                   cancel(3), 
                   delete(4),
                   none(99)
                }    
                
 Dot1agCfmMaintDomainNameType ::= TEXTUAL-CONVENTION
    STATUS      current
    DESCRIPTION
        "A value that represents a type (and thereby the format)
         of a Dot1agCfmMaintDomainName. The value can be one of
         the following:

         ieeeReserved(0)   Reserved for definition by IEEE 802.1
                           recommend to not use zero unless
                           absolutely needed.
          none(1)           No format specified, usually because
                            there is not (yet) a Maintenance
                            Domain Name. In this case, a zero
                            length OCTET STRING for the Domain
                            Name field is acceptable.
          dnsLikeName(2)    Domain Name like string, globally unique
                           text string derived from a DNS name.
          macAddrAndUint(3) MAC address + 2-octet (unsigned) integer.
          charString(4)     RFC2579 DisplayString, except that the
                            character codes 0-31 (decimal) are not
                            used.
          ieeeReserved(xx)  Reserved for definition by IEEE 802.1
                            xx values can be [5..31] and [64..255]
          ituReserved(xx)   Reserved for definition by ITU-T Y.1731
                            xx values range from [32..63]
         "
    REFERENCE
         "802.1ag clause 21.6.5, Table 21-19"
    SYNTAX      INTEGER {
                   none              (1),
                   dnsLikeName       (2),
                   macAddressAndUint (3),
                   charString        (4)
                }

 Dot1agCfmMaintDomainName ::= TEXTUAL-CONVENTION
    STATUS      current
    DESCRIPTION
        "Denotes a generic Maintenance Domain Name."
    REFERENCE
        "802.1ag clause 21.6.5"
    SYNTAX OCTET STRING (SIZE(1..43))

 Dot1agCfmMaintAssocNameType ::= TEXTUAL-CONVENTION
    STATUS      current
    DESCRIPTION
         "A value that represents a type (and thereby the format)
          of a Dot1agCfmMaintAssocName. The value can be one of
          the following:

          ieeeReserved(0)  Reserved for definition by IEEE 802.1
                           recommend to not use zero unless
                           absolutely needed.
          primaryVid(1)    Primary VLAN ID.
                           12 bits represented in a 2-octet integer:
                           - 4 least significant bits of the first
                             byte contains the 4 most significant
                             bits of the 12 bits primary VID
                           - second byte contains the 8 least
                             significant bits of the primary VID

                                0 1 2 3 4 5 6 7 8
                                +-+-+-+-+-+-+-+-+
                                |0 0 0 0| (MSB) |
                                +-+-+-+-+-+-+-+-+
                                |  VID   LSB    |
                                +-+-+-+-+-+-+-+-+

          charString(2)    RFC2579 DisplayString, except that the
                           character codes 0-31 (decimal) are not
                           used. (1..45) octets
                           unsignedInt16 (3) 2-octet integer/big endian
          rfc2865VpnId(4)  RFC 2685 VPN ID
                           3 octet VPN authority Organizationally
                           Unique Identifier followed by 4 octet VPN
                           index identifying VPN according to the OUI:

                                0 1 2 3 4 5 6 7 8
                                +-+-+-+-+-+-+-+-+
                                | VPN OUI (MSB) |
                                +-+-+-+-+-+-+-+-+
                                |   VPN OUI     |
                                +-+-+-+-+-+-+-+-+
                                | VPN OUI (LSB) |
                                +-+-+-+-+-+-+-+-+
                                |VPN Index (MSB)|
                                +-+-+-+-+-+-+-+-+
                                |  VPN Index    |
                                +-+-+-+-+-+-+-+-+
                                |  VPN Index    |
                                +-+-+-+-+-+-+-+-+
                                |VPN Index (LSB)|
                                +-+-+-+-+-+-+-+-+

          ieeeReserved(xx) Reserved for definition by IEEE 802.1
                           xx values can be [5..31] and [64..255]
          ituReserved(xx)  Reserved for definition by ITU-T Y.1731
                           xx values range from [32..63]
         "
    REFERENCE
         "802.1ag clause 21.6.5.4, Table 21-20"
    SYNTAX     INTEGER {
                  primaryVid    (1),
                  charString    (2),
                  unsignedInt16 (3),
                  rfc2865VpnId  (4),
                  iccBased      (32)
               }

 Dot1agCfmMaintAssocName ::= TEXTUAL-CONVENTION
    STATUS      current
    DESCRIPTION
         "Denotes a generic Maintenance Association Name. It is the
          part of the Maintenance Association Identifier which is
          unique within the Maintenance Domain Name and is appended
          to the Maintenance Domain Name to form the Maintenance
          Association Identifier (MAID).
         "
    REFERENCE
         "802.1ag clauses 21.6.5.4, 21.6.5.5, 21.6.5.6"
    SYNTAX      OCTET STRING (SIZE(1..45))

 CfmFrameLossRatio ::= TEXTUAL-CONVENTION
    DISPLAY-HINT "d-4"
    STATUS      current
    DESCRIPTION
        "Denotes Frame Loss Ratio in accuracy of four digits.
         So a value of 1000 here would mean 0.1% loss."
    SYNTAX      Unsigned32 (0..1000000)

 CfmFrameRatio ::= TEXTUAL-CONVENTION
    DISPLAY-HINT "d-2"
    STATUS      current
    DESCRIPTION
        "Denotes Ratio in accuracy of two digits.
         So a value of 10 here would mean 0.1%."
    SYNTAX      Unsigned32 (0..10000)

 CfmTimestampType ::= TEXTUAL-CONVENTION
    STATUS      current
    DESCRIPTION
        "Represents the Type of Timestamp (if required) to be added in CFM Frames
         software (1): For CFM frames timestamped by Software
         hardware (2): For CFM frames timestamped by Hardware"
    SYNTAX      INTEGER {
                   software(1),
                   hardware(2)
                }

--
--Global Attributes
--
 wwpLeosCfmState OBJECT-TYPE
    SYNTAX      INTEGER {
                                disabled(1),
                                enabled(2)
                        }
    MAX-ACCESS  read-write
    STATUS      current
    DESCRIPTION
        "This object allows the user to globally configure CFM state."
    ::= { wwpLeosCfmGlobal 1 } 
  
 wwpLeosCfmEtherType  OBJECT-TYPE
    SYNTAX      EthType
    MAX-ACCESS  read-write
    STATUS      current
    DESCRIPTION
        "This object specifies the Ethernet type for CFM frames."
    ::= { wwpLeosCfmGlobal 2 }
    
 wwpLeosCfmMEPHoldTime OBJECT-TYPE
    SYNTAX      Integer32
    MAX-ACCESS  read-write
    STATUS      current
    DESCRIPTION
        "This object specifies the time in milliseconds to hold a MEP in an inactive state."
    ::= { wwpLeosCfmGlobal 3 }                                                  
 
 wwpLeosCfmCcmAvailable OBJECT-TYPE
    SYNTAX      Counter32
    MAX-ACCESS  read-only
    STATUS      current
    DESCRIPTION
        "This object specifies the current CCM available."
    ::= { wwpLeosCfmGlobal 4 } 
    
 wwpLeosCfmY1731EtherType  OBJECT-TYPE
    SYNTAX      EthType
    MAX-ACCESS  read-write
    STATUS      current
    DESCRIPTION
        "This object specifies the Optional Alternate Ethernet type for Y.1731 frames."    
    ::= { wwpLeosCfmGlobal 5 } 
 
  wwpLeosCfmL2LoopDetectState OBJECT-TYPE
    SYNTAX      INTEGER {
                                off(1),
                                on(2)
                        }
    MAX-ACCESS  read-write
    STATUS      current
    DESCRIPTION
        "This object allows the user to globally configure CFM's Layer 2 Loop
        detection state.  Frames received by the switch that have a
        source MAC of the switch are discarded."
    ::= { wwpLeosCfmGlobal 6 } 
 
 
 wwpLeosCfmDot1adStrict OBJECT-TYPE
   SYNTAX INTEGER {
   					on(1), 
 					off(2)
 		   } 
   MAX-ACCESS   read-write 
   STATUS 	current
   DESCRIPTION
   		"Controls compliance of processing 802.1ad encapsulated CFM frames in accordance with the 8021.ag standard.
   		When on (1) CFM frames containing more than one VLAN tag are forwarded as normal data frames, bypassing processing  by MEPs and MIPs.
   		When off (2) CFM frames with multiple VLAN tags are subject to normal CFM processing."
   ::= { wwpLeosCfmGlobal 7}
  
  wwpLeosCfmMipLevelEnforcement OBJECT-TYPE  
   SYNTAX INTEGER {
   					on(1), 
 					off(2)
 		   } 
   MAX-ACCESS   read-write 
   STATUS 	 current
   DESCRIPTION
    	"Controls enforcement of a MIPs associated MD Level.
         When on (1), a MIP only processes CFM messages received at its level.
         When off (2), a MIP processes frames received at any level."
   ::= {wwpLeosCfmGlobal 8}
   
  wwpLeosCfmMipCcmDbState OBJECT-TYPE
    SYNTAX INTEGER {
                        enable(1),
                        disable(2)
                   }
    MAX-ACCESS   read-write 
    STATUS       current
    DESCRIPTION
                "The administrative state of the MIP CCM Database.  
                 A MIP only records CCMs in the MIP CCM Database when this object is set to enable (1)."
    ::= {wwpLeosCfmGlobal 9}

  --deprecated
  wwpLeosCfmLBMDefaultCount OBJECT-TYPE
    SYNTAX      Integer32
    MAX-ACCESS  read-write
    STATUS      deprecated
    DESCRIPTION
        "The global default loopback message count."
    ::= { wwpLeosCfmGlobal 10 }  
 
   --deprecated
  wwpLeosCfmLBMDefaultInterval OBJECT-TYPE
    SYNTAX      Integer32
    MAX-ACCESS  read-write
    STATUS      deprecated
    DESCRIPTION
        "The global default loopback message interval."
    ::= { wwpLeosCfmGlobal 11 } 

  --deprecated
  wwpLeosCfmLBMDefaultTimeout OBJECT-TYPE
    SYNTAX      Integer32
    MAX-ACCESS  read-write
    STATUS      deprecated
    DESCRIPTION
        "The global default loopback message timeout."
    ::= { wwpLeosCfmGlobal 12 }   

  --deprecated
 wwpLeosCfmFrameClassifierMode OBJECT-TYPE
    SYNTAX INTEGER {
                        etype(1),
                        etypeMd(2)
                   }
    MAX-ACCESS  read-write 
    STATUS      deprecated
    DESCRIPTION
        "Configures the hardware frame classification mode used to detect CFM
        and Y.1731 frames that should be sent to the CPU for processing.  Changing
        this mode causes a reboot of the device."
    ::= {wwpLeosCfmGlobal 13}  
 
 --Deprecated OIDs 14,15 in 5305 MIB   
  wwpLeosCfmGlobalLBMDefaultCount OBJECT-TYPE
    SYNTAX      Integer32
    MAX-ACCESS  read-write
    STATUS      current
    DESCRIPTION
        "The global default loopback message count."
    ::= { wwpLeosCfmGlobal 16 }  
   
  wwpLeosCfmGlobalLBMDefaultInterval OBJECT-TYPE
    SYNTAX      Integer32
    MAX-ACCESS  read-write
    STATUS      current
    DESCRIPTION
        "The global default loopback message interval."
    ::= { wwpLeosCfmGlobal 17 } 
    
  wwpLeosCfmGlobalLBMDefaultTimeout OBJECT-TYPE
    SYNTAX      Integer32
    MAX-ACCESS  read-write
    STATUS      current
    DESCRIPTION
        "The global default loopback message timeout."
    ::= { wwpLeosCfmGlobal 18 }   

 wwpLeosCfmGlobalFrameClassifierMode OBJECT-TYPE
    SYNTAX INTEGER {
                        etype(1),
                        etypeMd(2)
                   }
    MAX-ACCESS  read-write 
    STATUS      current
    DESCRIPTION
        "Configures the hardware frame classification mode used to detect CFM
        and Y.1731 frames that should be sent to the CPU for processing.  Changing
        this mode causes a reboot of the device."
    ::= {wwpLeosCfmGlobal 19}
    
  wwpLeosCfmGlobalSLMDefaultCount OBJECT-TYPE
    SYNTAX      Integer32
    MAX-ACCESS  read-write
    STATUS      current
    DESCRIPTION
        "The global default SLM message count."
    ::= { wwpLeosCfmGlobal 20 }  
   
  wwpLeosCfmGlobalSLMDefaultInterval OBJECT-TYPE
    SYNTAX      Integer32
    MAX-ACCESS  read-write
    STATUS      current
    DESCRIPTION
        "The global default SLM message interval."
    ::= { wwpLeosCfmGlobal 21 } 
    
  wwpLeosCfmGlobalSLMDefaultTimeout OBJECT-TYPE
    SYNTAX      Integer32
    MAX-ACCESS  read-write
    STATUS      current
    DESCRIPTION
        "The global default SLM message timeout."
    ::= { wwpLeosCfmGlobal 22 }    
    
  wwpLeosCfmGlobalDMMDefaultCount OBJECT-TYPE
    SYNTAX      Integer32
    MAX-ACCESS  read-write
    STATUS      current
    DESCRIPTION
        "The global default DMM message count."
    ::= { wwpLeosCfmGlobal 26 }  
   
  wwpLeosCfmGlobalDMMDefaultInterval OBJECT-TYPE
    SYNTAX      Integer32
    MAX-ACCESS  read-write
    STATUS      current
    DESCRIPTION
        "The global default DMM message interval."
    ::= { wwpLeosCfmGlobal 27 } 
    
  wwpLeosCfmGlobalDMMDefaultTimeout OBJECT-TYPE
    SYNTAX      Integer32
    MAX-ACCESS  read-write
    STATUS      current
    DESCRIPTION
        "The global default DMM message Rx timeout."
    ::= { wwpLeosCfmGlobal 28 } 
    
  wwpLeosCfmGlobalLMMDefaultCount OBJECT-TYPE
    SYNTAX      Integer32
    MAX-ACCESS  read-write
    STATUS      current
    DESCRIPTION
        "The global default DMM message count."
    ::= { wwpLeosCfmGlobal 29 }  
   
  wwpLeosCfmGlobalLMMDefaultInterval OBJECT-TYPE
    SYNTAX      Integer32
    MAX-ACCESS  read-write
    STATUS      current
    DESCRIPTION
        "The global default DMM message interval."
    ::= { wwpLeosCfmGlobal 30 } 
    
  wwpLeosCfmGlobalLMMDefaultTimeout OBJECT-TYPE
    SYNTAX      Integer32
    MAX-ACCESS  read-write
    STATUS      current
    DESCRIPTION
        "The global default LMM message Rx timeout."
    ::= { wwpLeosCfmGlobal 31 } 

  wwpLeosCfmGlobalVsAutoMepCreate OBJECT-TYPE
    SYNTAX      INTEGER
                {
                  on(0),
                  off(1)
                }                   
    MAX-ACCESS  read-write
    STATUS      current
    DESCRIPTION
        "This object specifies the state of VS automatic mep creation. 
         By default it is on(1) and not applicable for accelerated services."
    ::= { wwpLeosCfmGlobal 32 } 

  wwpLeosCfmGlobalSlmResponderAging OBJECT-TYPE
    SYNTAX      INTEGER
                {
                  off(0),
                  on(1)
                }                   
    MAX-ACCESS  read-only
    STATUS      current
    DESCRIPTION
        "This object specifies that implicit SLM respnder aging is enable or disabled.
         By default state is off(0) and aging is not applicable for user configured SLM Responders."
    ::= { wwpLeosCfmGlobal 33 } 
 
 --
 -- wwpLeosCfmGlobalStats
 --
  wwpLeosCfmStatsTotalTx OBJECT-TYPE
 	SYNTAX		Counter64
 	MAX-ACCESS	read-only
 	STATUS		current
 	DESCRIPTION	
 		"The number of frames sent."
 	::= { wwpLeosCfmGlobalStats 1 }
   
 wwpLeosCfmStatsTotalRx OBJECT-TYPE
 	SYNTAX		Counter64
 	MAX-ACCESS	read-only
 	STATUS		current
 	DESCRIPTION	
 		"The number of frames received."
 	::= { wwpLeosCfmGlobalStats 2 }

 wwpLeosCfmStatsTxFloodedFrames OBJECT-TYPE
 	SYNTAX		Counter64
 	MAX-ACCESS	read-only
 	STATUS		current
 	DESCRIPTION	
 		"The number of flooded frames sent."
 	::= { wwpLeosCfmGlobalStats 3 }
 
 wwpLeosCfmStatsTxFloodedIgnoredStpState  OBJECT-TYPE
 	SYNTAX		Counter64
 	MAX-ACCESS	read-only
 	STATUS		current
 	DESCRIPTION	
 		"The number of flooded ignored frames sent."
 	::= { wwpLeosCfmGlobalStats 4 }
 
 wwpLeosCfmStatsRxTotalValidFrames OBJECT-TYPE
 	SYNTAX		Counter64
 	MAX-ACCESS	read-only
 	STATUS		current
 	DESCRIPTION	
 		"The number of valid frames received."
 	::= { wwpLeosCfmGlobalStats 5 }
 
 wwpLeosCfmStatsRxTotalNotValidatedFrames OBJECT-TYPE
 	SYNTAX		Counter64
 	MAX-ACCESS	read-only
 	STATUS		current
 	DESCRIPTION	
 		"The number of not validated frames received."
 	::= { wwpLeosCfmGlobalStats 6 }
 
 wwpLeosCfmStatsRxTotalInValidFrames OBJECT-TYPE
 	SYNTAX		Counter64
 	MAX-ACCESS	read-only
 	STATUS		current
 	DESCRIPTION	
 		"The number of invalid frames received."
 	::= { wwpLeosCfmGlobalStats 7 }                         
 
 wwpLeosCfmTotalRxInvalidMessageOverflow OBJECT-TYPE
 	SYNTAX		Counter64
 	MAX-ACCESS	read-only
 	STATUS		current
 	DESCRIPTION	
 		"The number of invalid message overflow frames received."
 	::= { wwpLeosCfmGlobalStats 8 }
 
 wwpLeosCfmTotalRxInvalidPortStatusTLV OBJECT-TYPE
 	SYNTAX		Counter64
 	MAX-ACCESS	read-only
 	STATUS		current
 	DESCRIPTION	
 		"The number of invalid port status TLV received."
 	::= { wwpLeosCfmGlobalStats 9 }                                
 	
 wwpLeosCfmTotalRxInvalidInterfaceStatusTLV OBJECT-TYPE
 	SYNTAX		Counter64
 	MAX-ACCESS	read-only
 	STATUS		current
 	DESCRIPTION	
 		"The number of invalid interface status TLV received."
 	::= { wwpLeosCfmGlobalStats 10 }                 
 	
 wwpLeosCfmTotalRxInvalidSenderIDTLV OBJECT-TYPE
 	SYNTAX		Counter64
 	MAX-ACCESS	read-only
 	STATUS		current
 	DESCRIPTION	
 		"The number of invalid sender ID TLV received."
 	::= { wwpLeosCfmGlobalStats 11 }                 
 
  wwpLeosCfmRxAdminDisableDropped OBJECT-TYPE
  	SYNTAX Counter64
  	MAX-ACCESS read-only
  	STATUS current
  	DESCRIPTION 
  		"The number of frames dropped when in admin disable mode."
  	::= { wwpLeosCfmGlobalStats 12 }
  
--deprecated
  wwpLesoCfmRxInvalidEtypeDropped OBJECT-TYPE
  	SYNTAX Counter64
  	MAX-ACCESS read-only
  	STATUS deprecated
  	DESCRIPTION 
  		"The number of frames dropped when in admin disable mode."
  	::= { wwpLeosCfmGlobalStats 13 }
  
  wwpLeosCfmRxInvalidOpCodeDropped OBJECT-TYPE
  	SYNTAX Counter64
  	MAX-ACCESS read-only
  	STATUS current
  	DESCRIPTION 
  		"The number of received invalid opcode frames dropped."
  	::= { wwpLeosCfmGlobalStats 14 }
  	
  wwpLeosCfmRxSTPStateNotForwardingDropped OBJECT-TYPE
  	SYNTAX Counter64
  	MAX-ACCESS read-only
  	STATUS current
  	DESCRIPTION 
  		"The number of frames dropped when system is not in STP forwarding mode."
  	::= { wwpLeosCfmGlobalStats 15 } 
  
  wwpLeosCfmGlobalStatsClear	OBJECT-TYPE
  	SYNTAX INTEGER {
  			clear(1),
  			none(2)
  		}
  	MAX-ACCESS read-write
  	STATUS current
  	DESCRIPTION
  		"Setting this object to clear(1) clears statistics globally 
  		(global, service and MEP statistics). 
  		This object cannot be set to none."
  	::= { wwpLeosCfmGlobalStats 16 } 
  
  wwpLeosCfmGlobalLoopbackMsgStatsClear OBJECT-TYPE
  	SYNTAX INTEGER {
  			clear(1),
  			none(2)
  		}
  	MAX-ACCESS read-write
  	STATUS current
  	DESCRIPTION 
  		"Setting this object to clear(1) clears the loopback statistics 
  		globally (global, service and MEP statistics)."
  	::= { wwpLeosCfmGlobalStats 17 }  
  
  wwpLeosCfmGlobalLinkTraceMsgStatsClear  OBJECT-TYPE
  	SYNTAX INTEGER {
  			clear(1),
  			none(2)
  		}
  	MAX-ACCESS read-write
  	STATUS current
  	DESCRIPTION 
  		"Setting this object to clear(1) clears link trace statistics 
  		globally (global, service and MEP statistics)."
  	::= { wwpLeosCfmGlobalStats 18 } 
  
  wwpLeosCfmGlobalDelayMeasurementMsgStatsClear  OBJECT-TYPE
  	SYNTAX INTEGER {
  			clear(1),
  			none(2)
  		}
  	MAX-ACCESS read-write
  	STATUS current
  	DESCRIPTION 
  		"Setting this object to clear(1) clears delay measurement 
  		statistics globally (global, service and MEP statistics)."
  	::= { wwpLeosCfmGlobalStats 19 } 
  
  
  wwpLeosCfmGlobalLossMeasurementMsgStatsClear  OBJECT-TYPE
  	SYNTAX INTEGER {
  			clear(1),
  			none(2)
  		}
  	MAX-ACCESS read-write
  	STATUS current
  	DESCRIPTION 
  		"Setting this object to clear(1) clears loss measurement 
  		statistics globally (global, service and MEP statistics)."
  	::= { wwpLeosCfmGlobalStats 20 } 

  wwpLeosCfmTotalRxDropBlockedOppositeMep OBJECT-TYPE
  	SYNTAX Counter64
  	MAX-ACCESS read-only
  	STATUS current
  	DESCRIPTION 
  		"The number of received blocked by opposite MEP frames dropped."
  	::= { wwpLeosCfmGlobalStats 21 }   
  	
  wwpLeosCfmGlobalSLMMeasurementMsgStatsClear  OBJECT-TYPE
  	SYNTAX INTEGER {
  			clear(1),
  			none(2)
  		}
  	MAX-ACCESS read-write
  	STATUS current
  	DESCRIPTION 
  		"Setting this object to clear(1) clears SLM measurement 
  		statistics globally (global, service and MEP statistics)."
  	::= { wwpLeosCfmGlobalStats 22 } 

  wwpLeosCfmRxInvalidEtypeDropped OBJECT-TYPE
  	SYNTAX Counter64
  	MAX-ACCESS read-only
  	STATUS current
  	DESCRIPTION 
  		"The number of frames dropped when in admin disable mode."
  	::= { wwpLeosCfmGlobalStats 23 }

--
--wwpLeosCfmGlobalCCMStats
--  	
  wwpLeosCfmTotalTxCCM OBJECT-TYPE
  	SYNTAX Counter64
  	MAX-ACCESS read-only
  	STATUS current
  	DESCRIPTION 
  		"The total number of CCM frames sent."
  	::= { wwpLeosCfmGlobalCCMStats  1 }
  
  wwpLeosCfmTotalTxCCMFlooded OBJECT-TYPE
  	SYNTAX Counter64
  	MAX-ACCESS read-only
  	STATUS current
  	DESCRIPTION 
  		"The total number of flooded CCM frames sent."
  	::= { wwpLeosCfmGlobalCCMStats  2 }
  
  wwpLeosCfmTotalRxValidCCM OBJECT-TYPE
  	SYNTAX Counter64
  	MAX-ACCESS read-only
  	STATUS current
  	DESCRIPTION 
  		"The number of valid frames received."
  	::= { wwpLeosCfmGlobalCCMStats  3 }
  
  wwpLeosCfmTotalRxCCMInSequence OBJECT-TYPE
  	SYNTAX Counter64
  	MAX-ACCESS read-only
  	STATUS current
  	DESCRIPTION 
  		"The number of CCM frames received in sequence."
  	::= { wwpLeosCfmGlobalCCMStats  4 }
  
  wwpLeosCfmTotalRxCCMSequenceError OBJECT-TYPE
  	SYNTAX Counter64
  	MAX-ACCESS read-only
  	STATUS current
  	DESCRIPTION 
  		"The number of errored CCM frames received in sequence."
  	::= { wwpLeosCfmGlobalCCMStats  5 }
   
   wwpLeosCfmTotalCCMRxMDLevelXcon OBJECT-TYPE
  	SYNTAX Counter64
  	MAX-ACCESS read-only
  	STATUS current
  	DESCRIPTION 
  		"The number of MD Level CFM frames received."
  	::= { wwpLeosCfmGlobalCCMStats  6 }  
  	
  	wwpLeosCfmTotalCCMRxMAIDXcon OBJECT-TYPE
  	SYNTAX Counter64
  	MAX-ACCESS read-only
  	STATUS current
  	DESCRIPTION 
  		"The number of MAID Xcon CFM frames received."
  	::= { wwpLeosCfmGlobalCCMStats  7 } 
  
   wwpLeosCfmTotalRxCCMErrorOnMepId OBJECT-TYPE
  	SYNTAX Counter64
  	MAX-ACCESS read-only
  	STATUS current
  	DESCRIPTION 
  		"The number of frames dropped when in admin disable mode."
  	::= { wwpLeosCfmGlobalCCMStats  8 }
  
   wwpLeosCfmTotalRxCCMIntervalError OBJECT-TYPE
   	SYNTAX Counter64
  	MAX-ACCESS read-only
  	STATUS current
  	DESCRIPTION 
  		"The number of interval error frames received."
  	::= { wwpLeosCfmGlobalCCMStats  9 }
    
    wwpLeosCfmTotalRxInvalidCCM OBJECT-TYPE
    	SYNTAX Counter64
    	MAX-ACCESS read-only
    	STATUS current
    	DESCRIPTION
    		"The number of invalid CCM frames received."
        ::= { wwpLeosCfmGlobalCCMStats  10 } 
 
 --
 --wwpLeosCfmGlobalLoopbackStats
 --   
    wwpLeosCfmTotalTxLBM OBJECT-TYPE
    	SYNTAX Counter64
    	MAX-ACCESS read-only
    	STATUS current
    	DESCRIPTION
    		"The number of Loopback messages sent."
        ::= { wwpLeosCfmGlobalLoopbackStats  1 }
      
     wwpLeosCfmTotalTxLBR OBJECT-TYPE
     	SYNTAX Counter64
    	MAX-ACCESS read-only
    	STATUS current
    	DESCRIPTION
    		"The total number of Loopback Replies frames sent."
        ::= { wwpLeosCfmGlobalLoopbackStats  2 }
        
      wwpLeosCfmTotalRxInOderLBR OBJECT-TYPE
      	SYNTAX Counter64
    	MAX-ACCESS read-only
    	STATUS current
    	DESCRIPTION
    		"The total number of  In order LBR frames received."
        ::= { wwpLeosCfmGlobalLoopbackStats  3 } 
       
   wwpLeosCfmTotalRxOOOLBR OBJECT-TYPE
       	SYNTAX Counter64
    	MAX-ACCESS read-only
    	STATUS current
    	DESCRIPTION
    		"The number of Out of Order LBR frames received."
        ::= { wwpLeosCfmGlobalLoopbackStats  4 }
    
    wwpLeosCfmTotalRxContentMismatchLBR  OBJECT-TYPE
       	SYNTAX Counter64
    	MAX-ACCESS read-only
    	STATUS current
    	DESCRIPTION
    		"The number of Content Mismatch LBR frames received."
        ::= { wwpLeosCfmGlobalLoopbackStats  5 }         
     
     wwpLeosCfmTotalRxUnexpectedLBR  OBJECT-TYPE
       	SYNTAX Counter64
    	MAX-ACCESS read-only
    	STATUS current
    	DESCRIPTION
    		"The number of unexpected LBR frames received."
        ::= { wwpLeosCfmGlobalLoopbackStats  6 }
        
     wwpLeosCfmTotalRxInvalidLBR  OBJECT-TYPE
       	SYNTAX Counter64
    	MAX-ACCESS read-only
    	STATUS current
    	DESCRIPTION
    		"The number of invalid LBR frames received."
        ::= { wwpLeosCfmGlobalLoopbackStats  7 }
      
      wwpLeosCfmTotalRxvalidLBM OBJECT-TYPE
       	SYNTAX Counter64
    	MAX-ACCESS read-only
    	STATUS current
    	DESCRIPTION
    		"The number of valid LBM frames received."
        ::= { wwpLeosCfmGlobalLoopbackStats  8 }

      wwpLeosCfmTotalRxInvalidLBM OBJECT-TYPE
       	SYNTAX Counter64
    	MAX-ACCESS read-only
    	STATUS current
    	DESCRIPTION
    		"The number of invalid LBM frames received."
        ::= { wwpLeosCfmGlobalLoopbackStats  9 }
  
 --
 --wwpLeosCfmGlobalLinkTraceStats
 --      
      wwpLeosCfmTotalTxLTM OBJECT-TYPE
       	SYNTAX Counter64
    	MAX-ACCESS read-only
    	STATUS current
    	DESCRIPTION
    		"The number of LTM frames sent."
        ::= { wwpLeosCfmGlobalLinkTraceStats  1 }
      
      wwpLeosCfmTotalTxLTR OBJECT-TYPE
       	SYNTAX Counter64
    	MAX-ACCESS read-only
    	STATUS current
    	DESCRIPTION
    		"The total number of LTR frames sent."
        ::= { wwpLeosCfmGlobalLinkTraceStats  2 }
       
       wwpLeosCfmTotalRxValidLTM  OBJECT-TYPE
       	  SYNTAX Counter64
       	  MAX-ACCESS read-only 
       	  STATUS current
    	  DESCRIPTION
    		"The total number of valid LTM frames received."
        ::= { wwpLeosCfmGlobalLinkTraceStats  3 }
       
       wwpLeosCfmTotalRxValidLTR OBJECT-TYPE
       	SYNTAX Counter64
       	MAX-ACCESS read-only
       	STATUS current
    	DESCRIPTION
    		"The total number of valid LTR frames received."
        ::= { wwpLeosCfmGlobalLinkTraceStats  4 }   
        
       wwpLeosCfmTotalRxUnexpectedLTR  OBJECT-TYPE
       	SYNTAX Counter64
       	MAX-ACCESS read-only
       	STATUS current
    	DESCRIPTION
    		"The total number of unexpected LTR frames received."
        ::= { wwpLeosCfmGlobalLinkTraceStats  5 }                                                
        
      wwpLeosCfmTotalRxInvalidLTR OBJECT-TYPE
      	SYNTAX Counter64
       	MAX-ACCESS read-only
       	STATUS current
    	DESCRIPTION
    		"The total number of Invalid LTR frames received."
        ::= { wwpLeosCfmGlobalLinkTraceStats  6 }
      
       wwpLeosCfmInvalidLTRRelayAction   OBJECT-TYPE
       	SYNTAX Counter64
       	MAX-ACCESS read-only
       	STATUS current
    	DESCRIPTION
    		"The total number of Invalid LTR Action."
        ::= { wwpLeosCfmGlobalLinkTraceStats  7 }

      wwpLeosCfmTotalRxInvalidLTM OBJECT-TYPE
       	SYNTAX Counter64
       	MAX-ACCESS read-only
       	STATUS current
    	DESCRIPTION
    		"The total number of Invalid LTM frames received."
        ::= { wwpLeosCfmGlobalLinkTraceStats  8 }
       
       wwpLeosCfmRxUnresolvedLTM  OBJECT-TYPE
       	SYNTAX Counter64
       	MAX-ACCESS read-only
       	STATUS current
    	DESCRIPTION
    		"The total number of Unresolved LTM frames received."
        ::= { wwpLeosCfmGlobalLinkTraceStats  9 }
   
 --
 --wwpLeosCfmGlobalDelayMeasurementStats
 --       
        wwpLeosCfmTotalTxDMM OBJECT-TYPE
        	SYNTAX Counter64
        	MAX-ACCESS  read-only
        	STATUS current
        	DESCRIPTION
        		"The total number of Delay Measurements messages sent."
        	::= {wwpLeosCfmGlobalDelayMeasurementStats  1 }
        
        wwpLeosCfmTotalTxDMR OBJECT-TYPE
        	SYNTAX Counter64
        	MAX-ACCESS  read-only
        	STATUS current
        	DESCRIPTION
        		"The total number of Delay Measurements Reply sent."
        	::= {wwpLeosCfmGlobalDelayMeasurementStats  2 }
        
        wwpLeosCfmTotalRxDMM  OBJECT-TYPE
        	SYNTAX Counter64
        	MAX-ACCESS  read-only
        	STATUS current
        	DESCRIPTION
        		"The total number of Delay Measurements Messages received."
        	::= {wwpLeosCfmGlobalDelayMeasurementStats  3 }
        
        wwpLeosCfmTotalRxDMR  OBJECT-TYPE
        	SYNTAX Counter64
        	MAX-ACCESS  read-only
        	STATUS current
        	DESCRIPTION
        		"The total number of Delay Measurements Reply received."
        	::= {wwpLeosCfmGlobalDelayMeasurementStats  4 }  
--
-- wwpLeosCfmGlobalLossMeasurementStats
--        
        wwpLeosCfmTotalTxLMM  OBJECT-TYPE
        	SYNTAX Counter64
        	MAX-ACCESS  read-only
        	STATUS current
        	DESCRIPTION
        		"The total number of Loss Measurements messages sent."
        	::= {wwpLeosCfmGlobalLossMeasurementStats  1 }  
       
       wwpLeosCfmTotalTxLMR OBJECT-TYPE
        	SYNTAX Counter64
        	MAX-ACCESS  read-only
        	STATUS current
        	DESCRIPTION
        		"The total number of Loss Measurements Reply frames sent."
        	::= {wwpLeosCfmGlobalLossMeasurementStats 2 }  
        
       wwpLeosCfmTotalRxLMM OBJECT-TYPE
       		SYNTAX Counter64
       		MAX-ACCESS read-only
       		STATUS current
       		DESCRIPTION
       			"The total number of LMM received."
       	 	::= { wwpLeosCfmGlobalLossMeasurementStats  3 }
       	
       	wwpLeosCfmTotalRxLMR  OBJECT-TYPE
       		SYNTAX Counter64
       		MAX-ACCESS read-only
       		STATUS current
       		DESCRIPTION
       			"The total number of LMR received."
       	 	::= { wwpLeosCfmGlobalLossMeasurementStats  4 }     
       	 	
--
-- wwpLeosCfmGlobalSLMMeasurementStats
--        
        wwpLeosCfmTotalTxSLM  OBJECT-TYPE
        	SYNTAX Counter64
        	MAX-ACCESS  read-only
        	STATUS current
        	DESCRIPTION
        		"The total number of SLM Measurements messages sent."
        	::= {wwpLeosCfmGlobalSLMMeasurementStats  1 }  
       
       wwpLeosCfmTotalTxSLR OBJECT-TYPE
        	SYNTAX Counter64
        	MAX-ACCESS  read-only
        	STATUS current
        	DESCRIPTION
        		"The total number of SLM Measurements Reply frames sent."
        	::= {wwpLeosCfmGlobalSLMMeasurementStats 2 }  
        
       wwpLeosCfmTotalRxSLM OBJECT-TYPE
       		SYNTAX Counter64
       		MAX-ACCESS read-only
       		STATUS current
       		DESCRIPTION
       			"The total number of SLM received."
       	 	::= { wwpLeosCfmGlobalSLMMeasurementStats  3 }
       	
       	wwpLeosCfmTotalRxSLR  OBJECT-TYPE
       		SYNTAX Counter64
       		MAX-ACCESS read-only
       		STATUS current
       		DESCRIPTION
       			"The total number of SLR received."
       	 	::= { wwpLeosCfmGlobalSLMMeasurementStats  4 }


--
-- wwpLeosCfmGlobalCSFStats
--        
        wwpLeosCfmTotalTxCSF OBJECT-TYPE
           SYNTAX Counter64
           MAX-ACCESS read-only
           STATUS current
           DESCRIPTION 
               "The total number of CSF frames transmitted."
           ::= { wwpLeosCfmGlobalCSFStats  1 }

        wwpLeosCfmTotalTxCSFLos OBJECT-TYPE
           SYNTAX Counter64
           MAX-ACCESS read-only
           STATUS current
           DESCRIPTION 
               "The total number of CSF Los frames transmitted."
           ::= { wwpLeosCfmGlobalCSFStats  2 }

        wwpLeosCfmTotalTxCSFDci OBJECT-TYPE
           SYNTAX Counter64
           MAX-ACCESS read-only
           STATUS current
           DESCRIPTION 
               "The total number of CSF Dci frames transmitted."
           ::= { wwpLeosCfmGlobalCSFStats  3 }

        wwpLeosCfmTotalRxCSF OBJECT-TYPE
           SYNTAX Counter64
           MAX-ACCESS read-only
           STATUS current
           DESCRIPTION 
               "The total number of valid CSF frames received."
           ::= { wwpLeosCfmGlobalCSFStats  4 }

        wwpLeosCfmTotalRxCSFLos OBJECT-TYPE
           SYNTAX Counter64
           MAX-ACCESS read-only
           STATUS current
           DESCRIPTION 
               "The total number of CSF Los frames received."
           ::= { wwpLeosCfmGlobalCSFStats  5 }

        wwpLeosCfmTotalRxCSFDci OBJECT-TYPE
           SYNTAX Counter64
           MAX-ACCESS read-only
           STATUS current
           DESCRIPTION 
               "The total number of CSF Dci frames received."
           ::= { wwpLeosCfmGlobalCSFStats  6 }

        wwpLeosCfmTotalInvalidRxCSF OBJECT-TYPE
           SYNTAX Counter64
           MAX-ACCESS read-only
           STATUS current
           DESCRIPTION 
               "The total number of invalid CSF frames received."
           ::= { wwpLeosCfmGlobalCSFStats  7 }


--
-- wwpLeosCfmGlobalFrameBudgetTable
--  
  wwpLeosCfmGlobalControlModuleFrameBudget OBJECT-TYPE
  	  SYNTAX    Counter32
  	  MAX-ACCESS read-only
  	  STATUS 	   current
  	  DESCRIPTION
  		"Control Module Frame Budget .
  		Not applicable to 6.x"
  	::= { wwpLeosCfmGlobalFrameBudget 1 }
     	
  wwpLeosCfmGlobalFrameBudgetTable OBJECT-TYPE
  	SYNTAX SEQUENCE OF WwpLeosCfmGlobalFrameBudgetEntry
  	MAX-ACCESS not-accessible
  	STATUS current
  	DESCRIPTION
  		"Global Frame Budget Table"
  	::= { wwpLeosCfmGlobalFrameBudget 2 }  
  	
  wwpLeosCfmGlobalFrameBudgetEntry OBJECT-TYPE
  	SYNTAX WwpLeosCfmGlobalFrameBudgetEntry
  	MAX-ACCESS  not-accessible
    STATUS      current
    DESCRIPTION
           "An entry (conceptual row) in the wwpLeosCfmServiceTable.
            Not applicable to 39xx/51xx."
    INDEX {wwpLeosCfmGlobalFrameBudgetSlotIndex}
     ::= { wwpLeosCfmGlobalFrameBudgetTable 1 }
   
   WwpLeosCfmGlobalFrameBudgetEntry ::= SEQUENCE {
   		wwpLeosCfmGlobalFrameBudgetSlotIndex	Unsigned32,
   		wwpLeosCfmGlobalFrameBudgetValue		Counter32
   	}
 	wwpLeosCfmGlobalFrameBudgetSlotIndex	OBJECT-TYPE
 		SYNTAX 	    Unsigned32
 		MAX-ACCESS  not-accessible
 		STATUS 		current
 		DESCRIPTION
 			"Slot Index"
 		::= {    wwpLeosCfmGlobalFrameBudgetEntry 1}
 	
 	wwpLeosCfmGlobalFrameBudgetValue OBJECT-TYPE
 		SYNTAX Counter32
 		UNITS  "frames/sec"
 		MAX-ACCESS 	read-only
 		STATUS 	current
 		DESCRIPTION
 			"Frame budget value"
 		::= { wwpLeosCfmGlobalFrameBudgetEntry 2}
  	

 --
 -- CFM Service Table
 --                          
 wwpLeosCfmServiceTable OBJECT-TYPE
     SYNTAX     SEQUENCE OF WwpLeosCfmServiceEntry
     MAX-ACCESS not-accessible
     STATUS     current
     DESCRIPTION
            "The (conceptual) table listing the configuration
            parameters for the CFM Service Table.
            To create an entry in this table the following criteria
            must be followed:
            -wwpLeosCfmServiceType must be specified.
            -wwpLeosCfmServiceValue must be specified.
            -wwpLeosCfmServiceName must be specified.
            -wwpLeosCfmServiceStatus must be set to createAndGo.
            "  
     ::= { wwpLeosCfmService 1 }
                
 wwpLeosCfmServiceEntry OBJECT-TYPE
     SYNTAX      WwpLeosCfmServiceEntry
     MAX-ACCESS  not-accessible
     STATUS      current
     DESCRIPTION
           "An entry (conceptual row) in the wwpLeosCfmServiceTable."
     INDEX {wwpLeosCfmServiceIndex}
     ::= { wwpLeosCfmServiceTable 1 }
        
 WwpLeosCfmServiceEntry ::=  SEQUENCE {               
     wwpLeosCfmServiceIndex                             Unsigned32,
     wwpLeosCfmServiceType                              INTEGER,
     wwpLeosCfmServiceValue                             INTEGER,     
     wwpLeosCfmServiceAdminState                        INTEGER,
     wwpLeosCfmServiceOperState                         INTEGER,
     wwpLeosCfmServiceAlarmTime                         INTEGER,
     wwpLeosCfmServiceCCMInterval                       INTEGER,
     wwpLeosCfmServiceName                              DisplayString,
     wwpLeosCfmServiceMdLevel                           INTEGER,
     wwpLeosCfmServiceResetTime                         INTEGER,
     wwpLeosCfmServiceLastFaultCCM                      CfmDisplayString,     
     wwpLeosCfmServiceRMEPFailureFlag                   TruthValue,
     wwpLeosCfmServiceCCMErrorFlag                      TruthValue,
     wwpLeosCfmServiceCrossConnectErrorFlag             TruthValue,     
     wwpLeosCfmServiceNumMEP                            Counter32,
     wwpLeosCfmServiceNumRemoteMEP                      Counter32,
     wwpLeosCfmServiceNumActiveMEP                      Counter32,
     wwpLeosCfmServiceStatus                            RowStatus,
     wwpLeosCfmServiceNextMepId                         Unsigned32,
     wwpLeosCfmServiceAlarmPriority                     Unsigned32,
     wwpLeosCfmServiceNumCCMForFault                    Unsigned32,
     wwpLeosCfmServiceDMMInterval                       INTEGER,
     wwpLeosCfmServiceLMMInterval                       INTEGER,
     wwpLeosCfmServiceCCMLossStatsState                 INTEGER,
     wwpLeosCfmServiceCCMLossBucketInterval             INTEGER,
     wwpLeosCfmServiceRemoteMepDiscovery                INTEGER,
     wwpLeosCfmServiceTlvSenderIdType                   INTEGER,
     wwpLeosCfmServiceRMEPHoldTime                      Unsigned32,
     wwpLeosCfmServicePortStatusFlag                    TruthValue,
     wwpLeosCfmServiceRDIFlag                           TruthValue,
     wwpLeosCfmServiceInstabilityFlag                   TruthValue,   
     wwpLeosCfmServiceDefaultMEPType                    INTEGER,                      --deprecated
     wwpLeosCfmServiceMAID                              CfmMAID,            		  --deprecated
     wwpLeosCfmServiceMdIndex                           Unsigned32,                   --deprecated
     wwpLeosCfmServiceMaintAssocNameType                Dot1agCfmMaintAssocNameType,  --deprecated
     wwpLeosCfmServiceMaintAssocName                    Dot1agCfmMaintAssocName,      --deprecated
     wwpLeosCfmServiceCfmMAID                           CfmMAID, 
     wwpLeosCfmServiceCfmMdIndex                        Unsigned32,   
     wwpLeosCfmServiceCfmMaintAssocNameType             Dot1agCfmMaintAssocNameType,
     wwpLeosCfmServiceCfmMaintAssocName                 Dot1agCfmMaintAssocName,
     wwpLeosCfmServiceCfmDefaultMEPType   		INTEGER,
     wwpLeosCfmServiceY1731                             TruthValue,   
     wwpLeosCfmServiceAccelerated			TruthValue,
     wwpLeosCfmServiceCCMTxState                        INTEGER,
     wwpLeosCfmServiceRMEPAging                         TruthValue,
     wwpLeosCfmServiceMulticastDa                       TruthValue,
     wwpLeosCfmServiceChargedAgainstGlobalFrameBudget	TruthValue,
     wwpLeosCfmServiceCfmControlModuleFrameBudget       Counter32,
     wwpLeosCfmServiceCSFInterval                       INTEGER,
     wwpLeosCfmServiceCSFLosNum                         Unsigned32,
     wwpLeosCfmServiceCSFDciNum                         Unsigned32,
     wwpLeosCfmServiceYProtectionMonitoringState        TruthValue
   }

 wwpLeosCfmServiceIndex OBJECT-TYPE
     SYNTAX      Unsigned32 (1..65535) 
     MAX-ACCESS  read-create
     STATUS      current
     DESCRIPTION
             "A unique identifier for CFM service entry."
     ::= { wwpLeosCfmServiceEntry 1 }

 wwpLeosCfmServiceType OBJECT-TYPE
     SYNTAX      INTEGER {
                                mplsVs(1),
                                ethVs(2),
                                vlan(3),
                                pbtTunnel(4),
                                vs(5),
                                other(9)                                 
                                }
     MAX-ACCESS  read-create
     STATUS      current
     DESCRIPTION
             "This object is used to specify the service type.
              Interpretation of wwpLeosCfmServiceValue depends on the value of this MIB object.
              This MIB object along with wwpLeosCfmServiceValue must be unique for each entry in this table"
     ::= { wwpLeosCfmServiceEntry 2 } 
                
 wwpLeosCfmServiceValue OBJECT-TYPE
     SYNTAX       INTEGER (1..65535)
     MAX-ACCESS   read-create
     STATUS       current
     DESCRIPTION
             "This object is used to specify the service value.
              Interpretation of this object depends on the value of wwpLeosCfmServiceType.
              This MIB object along with wwpLeosCfmServiceType must be unique for each entry in this table"
     ::= { wwpLeosCfmServiceEntry 3 }
 
 wwpLeosCfmServiceAdminState OBJECT-TYPE
     SYNTAX       INTEGER  {
                                disabled(1),
                                enabled(2)
                          }
     MAX-ACCESS   read-write
     STATUS       current
     DESCRIPTION
             "The admin state of CFM for this service type."
     DEFVAL {enabled}
     ::= { wwpLeosCfmServiceEntry 4 }
 
 wwpLeosCfmServiceOperState OBJECT-TYPE
     SYNTAX       INTEGER  {
                                disabled(1),
                                enabled(2)
                          }
     MAX-ACCESS   read-only
     STATUS       current
     DESCRIPTION
             "The operational state of CFM for this service type."
     ::= { wwpLeosCfmServiceEntry 5 }
 
 wwpLeosCfmServiceAlarmTime OBJECT-TYPE
     SYNTAX       INTEGER (0..36000)
     MAX-ACCESS   read-write
     STATUS       current
     DESCRIPTION
             "This MIB object allows the user to set the time interval that a service fault detected
              by wwpLeosCfmServiceType must be present before triggering a fault alarm."
     --UNITS    {msec}
     ::= { wwpLeosCfmServiceEntry 6 }
     
 wwpLeosCfmServiceCCMInterval OBJECT-TYPE
     SYNTAX       INTEGER (0..7)
     MAX-ACCESS   read-write
     STATUS       current
     DESCRIPTION
             "This MIB object allows the user to set the CCM transmission interval index for the service specified by wwpLeosCfmServiceType.
              This determines the frequency at which CCMs are transmitted.  The length of the interval increases exponentially
              with the index value.  Setting the interval to 0 disables CCM transmission from all MEPs in the MA."
     ::= { wwpLeosCfmServiceEntry 7 }

 wwpLeosCfmServiceName OBJECT-TYPE
     SYNTAX       DisplayString (SIZE(1..41))
     MAX-ACCESS   read-create
     STATUS       current
     DESCRIPTION
             "This MIB object allows the user to set the CFM service name."
     ::= { wwpLeosCfmServiceEntry 9 }        

wwpLeosCfmServiceMdLevel OBJECT-TYPE
     SYNTAX       INTEGER (0..7)
     MAX-ACCESS   read-create
     STATUS       current
     DESCRIPTION
             "This MIB object sets the CFM service level which associates it with a Maintenance Domain."
     ::= { wwpLeosCfmServiceEntry 10 }        

wwpLeosCfmServiceResetTime OBJECT-TYPE
     SYNTAX       INTEGER (10..36000)
     MAX-ACCESS   read-write
     STATUS       current
     DESCRIPTION
             "This MIB object sets the time interval during which no service faults can be detected
              before the service resets a fault alarm."
     ::= { wwpLeosCfmServiceEntry 11 }           

wwpLeosCfmServiceLastFaultCCM OBJECT-TYPE
     SYNTAX       CfmDisplayString
     MAX-ACCESS   read-only
     STATUS       current
     DESCRIPTION
             "This MIB object shows last received CCM fault."
     ::= { wwpLeosCfmServiceEntry 12 }            

 wwpLeosCfmServiceRMEPFailureFlag OBJECT-TYPE
     SYNTAX       TruthValue
     MAX-ACCESS   read-only
     STATUS       current
     DESCRIPTION
             "This MIB object shows the RMEP failure flag."
     ::= { wwpLeosCfmServiceEntry 13 }        

wwpLeosCfmServiceCCMErrorFlag OBJECT-TYPE
     SYNTAX       TruthValue
     MAX-ACCESS   read-only
     STATUS       current
     DESCRIPTION
             "This MIB object shows the CCM Error flag."
     ::= { wwpLeosCfmServiceEntry 14 }        

wwpLeosCfmServiceCrossConnectErrorFlag OBJECT-TYPE
     SYNTAX       TruthValue
     MAX-ACCESS   read-only
     STATUS       current
     DESCRIPTION
             "This MIB object shows the cross-connect Error flag."
     ::= { wwpLeosCfmServiceEntry 15 }                 
 
wwpLeosCfmServiceNumMEP OBJECT-TYPE
     SYNTAX       Counter32
     MAX-ACCESS   read-only
     STATUS       current
     DESCRIPTION
             "This MIB object shows Number of MEPs."
     ::= { wwpLeosCfmServiceEntry 16 }        
 
wwpLeosCfmServiceNumRemoteMEP OBJECT-TYPE
     SYNTAX       Counter32
     MAX-ACCESS   read-only
     STATUS       current
     DESCRIPTION
             "This MIB object shows the Number of Remote MEPs."
     ::= { wwpLeosCfmServiceEntry 17 }        
 
 wwpLeosCfmServiceNumActiveMEP OBJECT-TYPE
     SYNTAX       Counter32
     MAX-ACCESS   read-only
     STATUS       current
     DESCRIPTION
             "This MIB object shows the Number of active MEPs."
     ::= { wwpLeosCfmServiceEntry 18 }         
         
 wwpLeosCfmServiceStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set this object to 'destroy'."
     ::= { wwpLeosCfmServiceEntry 19 }  
     
 wwpLeosCfmServiceNextMepId OBJECT-TYPE
     SYNTAX      Unsigned32 (1..8191) 
     MAX-ACCESS  read-create
     STATUS      current
     DESCRIPTION
             "This mib object specifies the next MEP Id for given service."
     ::= { wwpLeosCfmServiceEntry 20 }
     
  wwpLeosCfmServiceAlarmPriority OBJECT-TYPE
     SYNTAX      Unsigned32 (1..5) 
     MAX-ACCESS  read-write
     STATUS      current
     DESCRIPTION
             "This mib object specifies the alarm priority for given service."
     DEFVAL		{3}
     ::= { wwpLeosCfmServiceEntry 21 } 
     
  wwpLeosCfmServiceNumCCMForFault OBJECT-TYPE
     SYNTAX      Unsigned32 (1..255) 
     MAX-ACCESS  read-write
     STATUS      current
     DESCRIPTION
             "The number of CCM frames that must go undelivered 
              for the service to be declared as operationally down."
     DEFVAL      {3}
     ::= { wwpLeosCfmServiceEntry 22 }  
     
 wwpLeosCfmServiceDMMInterval OBJECT-TYPE
     SYNTAX       INTEGER (1..7)
     MAX-ACCESS   read-write
     STATUS       obsolete
     DESCRIPTION
             "This MIB object allows the user to set the DMM transmission interval index for the service specified by wwpLeosCfmServiceType.
              This determines the frequency at which DMMs are transmitted.  The length of the interval increases exponentially
              with the index value.

              Marking it obsolete as Dmm interval adjustment is now done either global or per delay test."
     ::= { wwpLeosCfmServiceEntry 23 }
     
 wwpLeosCfmServiceLMMInterval OBJECT-TYPE
     SYNTAX       INTEGER (1..7)
     MAX-ACCESS   read-write
     STATUS       current
     DESCRIPTION
             "This MIB object allows the user to set the LMM transmission interval index for the service specified by wwpLeosCfmServiceType.
              This determines the frequency at which LMMs are transmitted.  The length of the interval increases exponentially
              with the index value."
     ::= { wwpLeosCfmServiceEntry 24 }
 
 wwpLeosCfmServiceCCMLossStatsState OBJECT-TYPE
     SYNTAX       INTEGER  {
                                disabled(1),
                                enabled(2)
                          }
     MAX-ACCESS   read-write
     STATUS       current
     DESCRIPTION
             "This object specifies the operational state of CCM loss accounting
             for RMEPs learned by this service type."
     DEFVAL {enabled}
     ::= { wwpLeosCfmServiceEntry 25 } 
     
 wwpLeosCfmServiceCCMLossBucketInterval OBJECT-TYPE
     SYNTAX       INTEGER (1..60)
     MAX-ACCESS   read-write
     STATUS       current
     DESCRIPTION
             "This object specifies the interval in minutes that each of the 96
             CCM loss history buckets span.  The default is 15 minutes, which
             means the default history covers 24 hours."
     ::= { wwpLeosCfmServiceEntry 26 }
  
 wwpLeosCfmServiceRemoteMepDiscovery OBJECT-TYPE
     SYNTAX      INTEGER { 
                    disabled(1),
                    enabled(2)
                 }
     MAX-ACCESS read-write
     STATUS current
     DESCRIPTION
             "This object specifies whether remote MEPs should be discovered automatically.
              If this object is set to enable it causes remote MEPs to be discovered
              automatically and if set to disable does not discover remote MEPs."
     ::= { wwpLeosCfmServiceEntry 27 }   
 
 wwpLeosCfmServiceY1731 OBJECT-TYPE
     SYNTAX       TruthValue
     MAX-ACCESS   read-write
     STATUS       current
     DESCRIPTION
             "Specifies if y1731 is enabled for the service."
     ::= { wwpLeosCfmServiceEntry 28 }
      
  wwpLeosCfmServiceAccelerated OBJECT-TYPE
     SYNTAX       TruthValue
     MAX-ACCESS   read-create
     STATUS       current
     DESCRIPTION
             "Specifies if the service is supported in hardware ."
     ::= { wwpLeosCfmServiceEntry 49 }

 wwpLeosCfmServiceTlvSenderIdType OBJECT-TYPE
     SYNTAX      INTEGER {
                    none(1),
                    chassis(2),
                    manage(3),
                    chassisManage(4)
                 } 
     MAX-ACCESS  read-create
     STATUS      current
     DESCRIPTION
             "This mib object specifies the Sender Id Tlv Type."
     DEFVAL		{chassis}
     ::= { wwpLeosCfmServiceEntry 50 }
   
  wwpLeosCfmServiceRMEPHoldTime OBJECT-TYPE
     SYNTAX      Unsigned32 (0..3600000)
     MAX-ACCESS  read-create
     STATUS      current
     DESCRIPTION
             "This mib object specifies the Remote MEP hold time in milliseconds."
     DEFVAL		{2500}
     ::= { wwpLeosCfmServiceEntry 51 }

  wwpLeosCfmServiceCCMTxState OBJECT-TYPE
     SYNTAX      INTEGER {
                    disabled(1),
                    enabled(2)
                 }
     MAX-ACCESS  read-create
     STATUS      current
     DESCRIPTION
             "This mib object specifies the admin state of the CCM Tx."
     DEFVAL		{enabled}
     ::= { wwpLeosCfmServiceEntry 52 }

 wwpLeosCfmServicePortStatusFlag OBJECT-TYPE
     SYNTAX       TruthValue
     MAX-ACCESS   read-only
     STATUS       current
     DESCRIPTION
             "This mib object shows the Port Status defect flag."
     ::= { wwpLeosCfmServiceEntry 53 }        

 wwpLeosCfmServiceRDIFlag OBJECT-TYPE
     SYNTAX       TruthValue
     MAX-ACCESS   read-only
     STATUS       current
     DESCRIPTION
             "This mib object shows the RDI defect flag."
     ::= { wwpLeosCfmServiceEntry 54 }        

 wwpLeosCfmServiceInstabilityFlag OBJECT-TYPE
     SYNTAX       TruthValue
     MAX-ACCESS   read-only
     STATUS       current
     DESCRIPTION
             "This mib object shows the Instability defect flag."
     ::= { wwpLeosCfmServiceEntry 55 } 

  wwpLeosCfmServiceRMEPAging OBJECT-TYPE
     SYNTAX       TruthValue
     MAX-ACCESS   read-create
     STATUS       current
     DESCRIPTION
             "Controls automatic Remote MEP aging for the service."
     ::= { wwpLeosCfmServiceEntry 56 }

 --deprecated
 wwpLeosCfmServiceDefaultMEPType OBJECT-TYPE
     SYNTAX      INTEGER {
                            up(1),
                            down(2)                                 
                         }
     MAX-ACCESS  read-create
     STATUS      deprecated
     DESCRIPTION
             "This object is used to specify the type of all MEP's created for
              the service. Services of type PBT must specify a MEP type of 'down'."
     ::= { wwpLeosCfmServiceEntry 57 }

 --deprecated
 wwpLeosCfmServiceMAID OBJECT-TYPE
     SYNTAX      CfmMAID
     MAX-ACCESS  read-only
     STATUS      deprecated
     DESCRIPTION 
             "The MAID send by CCMs associated with the service."
     ::= { wwpLeosCfmServiceEntry 58 }

 --deprecated
wwpLeosCfmServiceMdIndex OBJECT-TYPE
     SYNTAX      Unsigned32
     MAX-ACCESS  read-write
     STATUS      deprecated
     DESCRIPTION
             "The unique index in the Maint Domain table."
     ::= { wwpLeosCfmServiceEntry 59 }

 --deprecated
wwpLeosCfmServiceMaintAssocNameType OBJECT-TYPE
     SYNTAX      Dot1agCfmMaintAssocNameType
     MAX-ACCESS  read-write
     STATUS      deprecated
     DESCRIPTION
             "The type (and thereby format) of the Maintenance Association Name."
     REFERENCE
             "802.1ag clauses 21.6.5.4"
     ::= { wwpLeosCfmServiceEntry 60 }
 
  --deprecated
 wwpLeosCfmServiceMaintAssocName OBJECT-TYPE
     SYNTAX Dot1agCfmMaintAssocName
     MAX-ACCESS read-write
     STATUS deprecated
     DESCRIPTION
             "The Short Maintenance Association name. The type/format of
              this object is determined by the value of the
              dot1agCfmMaNetNameType object."
     REFERENCE
             "802.1ag clauses 21.6.5.6, and Table 21-20"
     ::= { wwpLeosCfmServiceEntry 61 }    
  
  --  OIDs 62,63,64 deprecated in 5305 donot use these OIDs
   wwpLeosCfmServiceMulticastDa OBJECT-TYPE
     SYNTAX       TruthValue
     MAX-ACCESS   read-write
     STATUS       current
     DESCRIPTION
             "Specifies if multicast DA mode is enabled for the service."
     ::= { wwpLeosCfmServiceEntry 65 }
 
   --  OIDs 66,67,68,69 deprecated in 5305 donot use these OIDs
   wwpLeosCfmServiceChargedAgainstGlobalFrameBudget OBJECT-TYPE
  	SYNTAX       TruthValue
    MAX-ACCESS   read-only
    STATUS       current
    DESCRIPTION
             "This MIB object reflects if this service is charged against
             the global frame budget."
     ::= { wwpLeosCfmServiceEntry 71 } 

  wwpLeosCfmServiceCfmDefaultMEPType OBJECT-TYPE
     SYNTAX      INTEGER {
                            up(1),
                            down(2)                                 
                         }
     MAX-ACCESS  read-create
     STATUS      current
     DESCRIPTION
             "This object is used to specify the type of all MEP's created for
              the service. Services of type PBT must specify a MEP type of 'down'."
     ::= { wwpLeosCfmServiceEntry 72 }
     
  wwpLeosCfmServiceCfmMAID OBJECT-TYPE
     SYNTAX      CfmMAID
     MAX-ACCESS  read-only
     STATUS      current
     DESCRIPTION 
             "The MAID send by CCM's associated with the service."
     ::= { wwpLeosCfmServiceEntry 73 } 
     
  wwpLeosCfmServiceCfmMdIndex OBJECT-TYPE
     SYNTAX      Unsigned32
     MAX-ACCESS  read-write
     STATUS      current
     DESCRIPTION
             "The unique index in the Maint Domain table."
     ::= { wwpLeosCfmServiceEntry 74 } 
     
 wwpLeosCfmServiceCfmMaintAssocNameType OBJECT-TYPE
     SYNTAX      Dot1agCfmMaintAssocNameType
     MAX-ACCESS  read-write
     STATUS      current
     DESCRIPTION
             "The type (and thereby format) of the Maintenance Association Name."
     REFERENCE
             "802.1ag clauses 21.6.5.4"
     ::= { wwpLeosCfmServiceEntry 75 }  
     
   wwpLeosCfmServiceCfmMaintAssocName OBJECT-TYPE
     SYNTAX Dot1agCfmMaintAssocName
     MAX-ACCESS read-write
     STATUS current
     DESCRIPTION
             "The Short Maintenance Association name. The type/format of
              this object is determined by the value of the
              dot1agCfmMaNetNameType object."
     REFERENCE
             "802.1ag clauses 21.6.5.6, and Table 21-20"
     ::= { wwpLeosCfmServiceEntry 76 }  
 
   wwpLeosCfmServiceCfmControlModuleFrameBudget  OBJECT-TYPE
  	 SYNTAX       Counter32
     MAX-ACCESS   read-only
     STATUS       current
     DESCRIPTION
             "Cfm Frame budget for control module for the given service."
     ::= { wwpLeosCfmServiceEntry 77 } 

   wwpLeosCfmServiceCSFInterval OBJECT-TYPE
     SYNTAX       INTEGER (1..7)
     MAX-ACCESS   read-only
     STATUS       current
     DESCRIPTION
             "This MIB object shows the CSF transmission interval index for the service specified by wwpLeosCfmServiceType.
              This determines the frequency at which CSFs are transmitted.  The length of the interval increases exponentially
              with the index value."
     ::= { wwpLeosCfmServiceEntry 78 }

   wwpLeosCfmServiceCSFLosNum OBJECT-TYPE
     SYNTAX      Unsigned32 (1..255) 
     MAX-ACCESS  read-only
     STATUS      current
     DESCRIPTION
             "The number of CSF Los frames that must go undelivered 
              for the service to be declared as CSF Fault Clear."
     ::= { wwpLeosCfmServiceEntry 79 }  

   wwpLeosCfmServiceCSFDciNum OBJECT-TYPE
     SYNTAX      Unsigned32 (1..255) 
     MAX-ACCESS  read-only
     STATUS      current
     DESCRIPTION
             "The number of CSF DCI frames to be transmitted after CSF Los Frame Transmission stopped."
     ::= { wwpLeosCfmServiceEntry 80 }  

   wwpLeosCfmServiceYProtectionMonitoringState OBJECT-TYPE
     SYNTAX       TruthValue
     MAX-ACCESS   read-create
     STATUS       current
     DESCRIPTION
             "Specifies if Y-Protection is enabled for the service."
     ::= { wwpLeosCfmServiceEntry 81 }
      
  --
 -- CFM Service Frame Budget Table
 --                           
 wwpLeosCfmServiceFrameBudgetTable OBJECT-TYPE
     SYNTAX     SEQUENCE OF WwpLeosCfmServiceFrameBudgetEntry
     MAX-ACCESS not-accessible
     STATUS     current
     DESCRIPTION
            "The (conceptual) table listing the config 
            parameters for the CFM service frame budget table."  
     ::= { wwpLeosCfmServiceFrameBudget 1 }
                
 wwpLeosCfmServiceFrameBudgetEntry OBJECT-TYPE
     SYNTAX      WwpLeosCfmServiceFrameBudgetEntry
     MAX-ACCESS  not-accessible
     STATUS      current
     DESCRIPTION
           "An entry (conceptual row) in the wwpLeosCfmServiceFrameBudgetTable."
     INDEX {wwpLeosCfmServiceIndex, wwpLeosCfmSlotIndex}
     ::= { wwpLeosCfmServiceFrameBudgetTable 1 }
        
 WwpLeosCfmServiceFrameBudgetEntry ::=  SEQUENCE {           
              
     wwpLeosCfmSlotIndex                        INTEGER,
     wwpLeosCfmServiceFrameBudgetSlot			 Counter32
     }

  wwpLeosCfmSlotIndex  OBJECT-TYPE
     SYNTAX       INTEGER(0..8) 
     MAX-ACCESS   not-accessible
     STATUS       current
     DESCRIPTION
             "This object identifies the slot number."
     ::= { wwpLeosCfmServiceFrameBudgetEntry 1 } 
  
  wwpLeosCfmServiceFrameBudgetSlot   OBJECT-TYPE
  	 SYNTAX       Counter32
  	 UNITS 		  "frames/sec"
     MAX-ACCESS   read-only
     STATUS       current
     DESCRIPTION
             "This object specifies the CFM frame budget for the slot for the given service."
     ::= { wwpLeosCfmServiceFrameBudgetEntry 2 } 
  
 --
 -- CFM MIP Table
 --                          
 wwpLeosCfmMipTable OBJECT-TYPE
     SYNTAX     SEQUENCE OF WwpLeosCfmMipEntry
     MAX-ACCESS not-accessible
     STATUS     obsolete
     DESCRIPTION
            "The (conceptual) table listing the configuration 
            parameters for the CFM MIP Table. 
            This table is not applicable if wwpLeosCfmServiceType is set to pbtTunnel. 
            Any Get/Set/Walk returns an error.
            This table is marked as obsolete as the functionality is
            shifted to wwpLeosCfmExtMipEntry." 
     ::= { wwpLeosCfmMIP 1 }
                
 wwpLeosCfmMipEntry OBJECT-TYPE
     SYNTAX      WwpLeosCfmMipEntry
     MAX-ACCESS  not-accessible
     STATUS      obsolete
     DESCRIPTION
           "An entry (conceptual row) in the wwpLeosCfmMipTable."
     INDEX {wwpLeosCfmMipVid, wwpLeosCfmMipPort}
     ::= { wwpLeosCfmMipTable 1 }
                
 WwpLeosCfmMipEntry ::=  SEQUENCE { 
     wwpLeosCfmMipVid                     	INTEGER,
     wwpLeosCfmMipPort                    	INTEGER,
     wwpLeosCfmMipLevel                   	INTEGER,
     wwpLeosCfmMipStatus                  	RowStatus
 }

 wwpLeosCfmMipVid OBJECT-TYPE
     SYNTAX      INTEGER (0..24576)
     MAX-ACCESS  read-only
     STATUS      obsolete
     DESCRIPTION
             "This object is the index in the table and is used to specify the
              VLAN service type for which intermediate maintenance points can be created."
     ::= { wwpLeosCfmMipEntry 1 }
 
 wwpLeosCfmMipPort OBJECT-TYPE
     SYNTAX      INTEGER (1..65535)
     MAX-ACCESS  read-only
     STATUS      obsolete
     DESCRIPTION
             "This object is used as index in the table and is used to specify the
              port."
     ::= { wwpLeosCfmMipEntry 2 }
                    
 wwpLeosCfmMipLevel OBJECT-TYPE
     SYNTAX       INTEGER (0..7)
     MAX-ACCESS   read-create
     STATUS       obsolete
     DESCRIPTION
             "This object is used to specify the level attribute."
     ::= { wwpLeosCfmMipEntry 3 }

 wwpLeosCfmMipStatus OBJECT-TYPE
     SYNTAX       RowStatus
     MAX-ACCESS   read-create
     STATUS       obsolete
     DESCRIPTION
         "Used to manage the creation and deletion of the conceptual rows in this table.
	 To create a row in this table, set this object to 'createAndGo'.
	 To delete a row in this table, set it to 'destroy'."
     ::= { wwpLeosCfmMipEntry 4 }
 
 --
 --  Link Trace Message table
 --  
 wwpLeosCfmLinkTraceMsgTable OBJECT-TYPE
     SYNTAX     SEQUENCE OF WwpLeosCfmLinkTraceMsgEntry
     MAX-ACCESS not-accessible
     STATUS     obsolete
     DESCRIPTION
            "The (conceptual) table listing the configuration 
            parameters for the LinkTraceMsg.
            Not applicable to 6.x.
            This table is marked as obsolete as the functionality 
            shifted to wwpLeosCfmExtLinkTraceMsgTable."  
     ::= { wwpLeosCfmLinkTrace 1 }
                
 wwpLeosCfmLinkTraceMsgEntry OBJECT-TYPE
     SYNTAX      WwpLeosCfmLinkTraceMsgEntry
     MAX-ACCESS  not-accessible
     STATUS      obsolete
     DESCRIPTION
           "An entry (conceptual row) in the wwpLeosCfmLinkTraceMsgTable."
     INDEX {wwpLeosCfmServiceIndex, wwpLeosCfmLinkTraceMsgPortId}
     ::= { wwpLeosCfmLinkTraceMsgTable 1 }
                
 WwpLeosCfmLinkTraceMsgEntry ::=  SEQUENCE { 
     wwpLeosCfmLinkTraceMsgPortId             	INTEGER,
     wwpLeosCfmLinkTraceMsgTargetMEPID        	INTEGER,
     wwpLeosCfmLinkTraceMsgTargetMacAddr      	MacAddress,
     wwpLeosCfmLinkTraceMsgTTL                	INTEGER,
     wwpLeosCfmLinkTraceMsgSequenceNumber       Integer32,
     wwpLeosCfmLinkTraceMsgRowStatus          	RowStatus,
     wwpLeosCfmLinkTraceMsgPriority             INTEGER,
     wwpLeosCfmLinkTraceMsgServiceName          DisplayString,
     wwpLeosCfmLinkTraceMsgSubPortName          DisplayString,
     wwpLeosCfmLinkTraceMsgVsIndex              Unsigned32,
     wwpLeosCfmLinkTraceMsgTotalTxLtm           Unsigned32,
     wwpLeosCfmLinkTraceMsgTotalRxLtr           Unsigned32   
 }

 wwpLeosCfmLinkTraceMsgPortId OBJECT-TYPE
     SYNTAX       INTEGER (1..65535)
     MAX-ACCESS   not-accessible
     STATUS       obsolete
     DESCRIPTION
             "This object is used to specify the port."
     ::= { wwpLeosCfmLinkTraceMsgEntry 1 }
 
 wwpLeosCfmLinkTraceMsgTargetMEPID OBJECT-TYPE
     SYNTAX       INTEGER (1..8191)
     MAX-ACCESS   read-create
     STATUS       obsolete
     DESCRIPTION
             "This object is used to specify the target MEPID.
              This object should only be set if wwpLeosCfmLinkTraceMsgTargetMacAddr is not specified else 
              an error is returned."
     ::= { wwpLeosCfmLinkTraceMsgEntry 2 }
     
 wwpLeosCfmLinkTraceMsgTargetMacAddr OBJECT-TYPE
     SYNTAX       MacAddress
     MAX-ACCESS   read-create
     STATUS       obsolete
     DESCRIPTION
             "This object is used to specify the target MacAddress to be used when sending link LinkMsg.
              This object should only be set if wwpLeosCfmLinkTraceMsgTargetMEPID is not specified else 
              an error is returned."
     ::= { wwpLeosCfmLinkTraceMsgEntry 3 }
     
 wwpLeosCfmLinkTraceMsgTTL OBJECT-TYPE
     SYNTAX       INTEGER (1..255)
     MAX-ACCESS   read-create
     STATUS       obsolete
     DESCRIPTION
             "This object is used to specify the TTL to be used when sending link LinkTraceMsg."
     ::= { wwpLeosCfmLinkTraceMsgEntry 4 }
 
 wwpLeosCfmLinkTraceMsgSequenceNumber OBJECT-TYPE
     SYNTAX       Integer32
     MAX-ACCESS   read-only
     STATUS       obsolete
     DESCRIPTION
             "This object is used to specify the sequence number in the linkTraceMsg."
     ::= { wwpLeosCfmLinkTraceMsgEntry 5 }

 wwpLeosCfmLinkTraceMsgRowStatus OBJECT-TYPE
     SYNTAX       RowStatus
     MAX-ACCESS   read-create
     STATUS       obsolete
     DESCRIPTION
             "Used to manage the creation and deletion of the conceptual rows in this table.
	     To create a row in this table, set this object to 'createAndGo'.
	     To delete a row in this table, set this to 'destroy'."
     ::= { wwpLeosCfmLinkTraceMsgEntry 6 }

  wwpLeosCfmLinkTraceMsgPriority OBJECT-TYPE
     SYNTAX      INTEGER (0..7) 
     MAX-ACCESS  read-create
     STATUS      obsolete
     DESCRIPTION
             "This object is used to specify the priority to be used 
              when sending LinkTraceMsg. "
     DEFVAL {7}
     ::= { wwpLeosCfmLinkTraceMsgEntry 7 } 
     
  wwpLeosCfmLinkTraceMsgServiceName OBJECT-TYPE
     SYNTAX      DisplayString (SIZE(1..41))
     MAX-ACCESS  read-only
     STATUS      obsolete
     DESCRIPTION
             "This object is used to specify the service to be used when
              sending LinkTraceMsg."
     ::= { wwpLeosCfmLinkTraceMsgEntry 50 }

 wwpLeosCfmLinkTraceMsgSubPortName OBJECT-TYPE
     SYNTAX      DisplayString (SIZE(0..31))
     MAX-ACCESS  read-only
     STATUS      obsolete
     DESCRIPTION
             "This object represents the sub-port name where the LinkTraceMsg
              was sent."
     ::= { wwpLeosCfmLinkTraceMsgEntry 52 }

 wwpLeosCfmLinkTraceMsgVsIndex OBJECT-TYPE
     SYNTAX      Unsigned32 
     MAX-ACCESS  read-only
     STATUS      obsolete
     DESCRIPTION
             "This object represents the virtual switch where the LinkTraceMsg was sent."
     ::= { wwpLeosCfmLinkTraceMsgEntry 53 }

 wwpLeosCfmLinkTraceMsgTotalTxLtm OBJECT-TYPE
     SYNTAX      Unsigned32
     MAX-ACCESS  read-only
     STATUS      obsolete
     DESCRIPTION
             "This object represents the total LinkTraceMsg were sent."
     ::= { wwpLeosCfmLinkTraceMsgEntry 54 }

 wwpLeosCfmLinkTraceMsgTotalRxLtr OBJECT-TYPE
     SYNTAX      Unsigned32
     MAX-ACCESS  read-only
     STATUS      obsolete
     DESCRIPTION
             "This object represents the total LinkTraceMsg were received
              from the LinkTraceResponse."
     ::= { wwpLeosCfmLinkTraceMsgEntry 55 }

  
 --
 --  Link Trace Message Reply table
 --  
 wwpLeosCfmLinkTraceMsgReplyTable OBJECT-TYPE
     SYNTAX     SEQUENCE OF WwpLeosCfmLinkTraceMsgReplyEntry
     MAX-ACCESS not-accessible
     STATUS     obsolete
     DESCRIPTION
            "The (conceptual) table listing the display 
            parameters for the LinkTrace Msg Reply.
            This table is marked as obsolete as the functionality
            shifted to wwpLeosCfmExtLinkTraceMsgReplyTable."
     ::= { wwpLeosCfmLinkTrace 2 }
                
  wwpLeosCfmLinkTraceMsgReplyEntry OBJECT-TYPE
     SYNTAX      WwpLeosCfmLinkTraceMsgReplyEntry
     MAX-ACCESS  not-accessible
     STATUS      obsolete
     DESCRIPTION
           "An entry (conceptual row) in the wwpLeosCfmLinkTraceMsgReplyTable."  

     INDEX {wwpLeosCfmServiceIndex, wwpLeosCfmLinkTraceMsgPortId, wwpLeosCfmLinkTraceMsgReplyTTL, wwpLeosCfmLinkTraceMsgReplyTTLIndex}
     ::= { wwpLeosCfmLinkTraceMsgReplyTable 1 }
                
  WwpLeosCfmLinkTraceMsgReplyEntry ::=  SEQUENCE {           
         wwpLeosCfmLinkTraceMsgReplyTTL                      	Integer32,
         wwpLeosCfmLinkTraceMsgReplyTTLIndex                    Unsigned32,
         wwpLeosCfmLinkTraceMsgReplySequenceNumber              Integer32,
         wwpLeosCfmLinkTraceMsgReplyMPMacAddr                   MacAddress,
         wwpLeosCfmLinkTraceMsgReplyMEPID                       Integer32,
         wwpLeosCfmLinkTraceMsgReplyTargetMacAddr               MacAddress,
         wwpLeosCfmLinkTraceMsgReplyRelayAction                 INTEGER,
         wwpLeosCfmLinkTraceMsgReplyIngressPort                 INTEGER,
         wwpLeosCfmLinkTraceMsgReplyIngressAction               INTEGER,
         wwpLeosCfmLinkTraceMsgReplyEgressPort                  INTEGER,
         wwpLeosCfmLinkTraceMsgReplyEgressAction                INTEGER,
         wwpLeosCfmLinkTraceMsgReplyIngressPortStr				DisplayString,
         wwpLeosCfmLinkTraceMsgReplyEgressPortStr				DisplayString,                
         wwpLeosCfmLinkTraceMsgReplyIngressMacAddr              MacAddress,
         wwpLeosCfmLinkTraceMsgReplyEgressMacAddr               MacAddress
  }
  
  wwpLeosCfmLinkTraceMsgReplyTTL OBJECT-TYPE
     SYNTAX       Integer32 (0..255)
     MAX-ACCESS   read-only
     STATUS       obsolete
     DESCRIPTION
             "This object is used to specify the ttl of the received LinkTrace msg reply."
     ::= { wwpLeosCfmLinkTraceMsgReplyEntry 1 }
     
  wwpLeosCfmLinkTraceMsgReplyTTLIndex OBJECT-TYPE
     SYNTAX       Unsigned32 (1..24576)
     MAX-ACCESS   read-only
     STATUS       obsolete
     DESCRIPTION
             "This object provides an additional index when multiple LinkTrace messages are received with the same TTL."
     ::= { wwpLeosCfmLinkTraceMsgReplyEntry 2 }
  
  wwpLeosCfmLinkTraceMsgReplySequenceNumber OBJECT-TYPE
     SYNTAX       Integer32
     MAX-ACCESS   read-only
     STATUS       obsolete
     DESCRIPTION
             "This object is used to specify the sequence number of the received LinkTrace msg reply."
     ::= { wwpLeosCfmLinkTraceMsgReplyEntry 3 }

  wwpLeosCfmLinkTraceMsgReplyMPMacAddr OBJECT-TYPE
     SYNTAX       MacAddress
     MAX-ACCESS   read-only
     STATUS       obsolete
     DESCRIPTION
             "This object is used to specify the mac address of the MP of received LinkTrace msg reply."
     ::= { wwpLeosCfmLinkTraceMsgReplyEntry 4 }

  wwpLeosCfmLinkTraceMsgReplyMEPID OBJECT-TYPE
     SYNTAX       Integer32
     MAX-ACCESS   read-only
     STATUS       obsolete
     DESCRIPTION
             "This object is used to specify the MEP ID of the received LinkTrace msg reply."
     ::= { wwpLeosCfmLinkTraceMsgReplyEntry 5 }

  wwpLeosCfmLinkTraceMsgReplyTargetMacAddr OBJECT-TYPE
     SYNTAX       MacAddress
     MAX-ACCESS   read-only
     STATUS       obsolete
     DESCRIPTION
             "This object is used to specify the Target Mac address of the received LinkTrace msg reply."
     ::= { wwpLeosCfmLinkTraceMsgReplyEntry 6 }
     
  wwpLeosCfmLinkTraceMsgReplyRelayAction OBJECT-TYPE
     SYNTAX       INTEGER   {
                                        invalid(1), 
                                        unknown(2),
                                        fdb(3),
                                        mpdb(4),
                                        noLearn(5),
                                        hit(6)
                            }     
     MAX-ACCESS   read-only
     STATUS       obsolete
     DESCRIPTION
             "This object is used to specify the message reply relay action."
     ::= { wwpLeosCfmLinkTraceMsgReplyEntry 7 }
  
  wwpLeosCfmLinkTraceMsgReplyIngressPort  OBJECT-TYPE
     SYNTAX       INTEGER  (1..65535)
     MAX-ACCESS   read-only
     STATUS       obsolete
     DESCRIPTION
             "This object is used to specify the message reply ingress port."
     ::= { wwpLeosCfmLinkTraceMsgReplyEntry 8 }
 
  wwpLeosCfmLinkTraceMsgReplyIngressAction  OBJECT-TYPE
     SYNTAX       INTEGER  {
                                        ok(1),
                                        blocked(2),
                                        vid(3),
                                        down(4),
                                        none(5)
                           }
     MAX-ACCESS   read-only
     STATUS       obsolete
     DESCRIPTION
             "This object is used to specify the message reply ingress action."
     ::= { wwpLeosCfmLinkTraceMsgReplyEntry 9 }
 
  wwpLeosCfmLinkTraceMsgReplyEgressPort  OBJECT-TYPE
     SYNTAX       INTEGER  (1..65535)
     MAX-ACCESS   read-only
     STATUS       obsolete
     DESCRIPTION
             "This object is used to specify the message reply egress port."
     ::= { wwpLeosCfmLinkTraceMsgReplyEntry 10 }
  
  wwpLeosCfmLinkTraceMsgReplyEgressAction  OBJECT-TYPE
     SYNTAX       INTEGER  {
                                none(1),
                                ttl(2),
                                down(3),
                                blocked(4),
                                vid(5),
                                ok(6)
                                }
     MAX-ACCESS   read-only
     STATUS       obsolete
     DESCRIPTION
             "This object is used to specify the message reply egress action."
     ::= { wwpLeosCfmLinkTraceMsgReplyEntry 11 }
  
  wwpLeosCfmLinkTraceMsgReplyIngressPortStr OBJECT-TYPE
     SYNTAX       DisplayString (SIZE(1..8))
     MAX-ACCESS   read-only
     STATUS       obsolete
     DESCRIPTION
             "This mib object is used to specify the message reply ingress port."
     ::= { wwpLeosCfmLinkTraceMsgReplyEntry 12 }        
 
 wwpLeosCfmLinkTraceMsgReplyEgressPortStr OBJECT-TYPE
     SYNTAX       DisplayString (SIZE(1..8))
     MAX-ACCESS   read-only
     STATUS       obsolete
     DESCRIPTION
             "This mib object is used to specify the message reply egress port."
     ::= { wwpLeosCfmLinkTraceMsgReplyEntry 13 }        

  wwpLeosCfmLinkTraceMsgReplyIngressMacAddr OBJECT-TYPE
     SYNTAX       MacAddress
     MAX-ACCESS   read-only
     STATUS       obsolete
     DESCRIPTION
             "This object is used to specify the message reply ingress mac address."
     ::= { wwpLeosCfmLinkTraceMsgReplyEntry 50 }
     
  wwpLeosCfmLinkTraceMsgReplyEgressMacAddr OBJECT-TYPE
     SYNTAX       MacAddress
     MAX-ACCESS   read-only
     STATUS       obsolete
     DESCRIPTION
             "This object is used to specify the message reply egress mac address."
     ::= { wwpLeosCfmLinkTraceMsgReplyEntry 51 }
 
  --
  -- Loopback Msg table
  -- 
  wwpLeosCfmLoopbackMsgTable OBJECT-TYPE
     SYNTAX     SEQUENCE OF WwpLeosCfmLoopbackMsgEntry
     MAX-ACCESS not-accessible
     STATUS     obsolete
     DESCRIPTION
            "The (conceptual) table listing the configuration 
            parameters for the LoopbackMsg.
            This table is marked as obsolete as the functionality
            shifted to wwpLeosCfmExtLoopbackMsgTable."  
     ::= { wwpLeosCfmLoopback 1 }
                
 wwpLeosCfmLoopbackMsgEntry OBJECT-TYPE
     SYNTAX      WwpLeosCfmLoopbackMsgEntry
     MAX-ACCESS  not-accessible
     STATUS      obsolete
     DESCRIPTION
           "An entry (conceptual row) in the wwpLeosCfmLoopbackMsgTable."
     INDEX {wwpLeosCfmServiceIndex, wwpLeosCfmLoopbackMsgPortId}
     ::= { wwpLeosCfmLoopbackMsgTable 1 }
                
 WwpLeosCfmLoopbackMsgEntry ::=  SEQUENCE { 
     wwpLeosCfmLoopbackMsgPortId                  INTEGER,
     wwpLeosCfmLoopbackMsgTargetMEPID             Unsigned32,
     wwpLeosCfmLoopbackMsgTargetMacAddr           MacAddress,
     wwpLeosCfmLoopbackMsgCount                   INTEGER,
     wwpLeosCfmLoopbackMsgData                    DisplayString,
     wwpLeosCfmLoopbackMsgPriority                INTEGER,     
     wwpLeosCfmLoopbackMsgDefaultInterval         INTEGER,
     wwpLeosCfmLoopbackMsgDefaultTimeout          INTEGER,
     wwpLeosCfmLoopbackMsgRowStatus               RowStatus     
 }

 wwpLeosCfmLoopbackMsgPortId OBJECT-TYPE
     SYNTAX       INTEGER (1..65535)
     MAX-ACCESS   read-only
     STATUS       obsolete
     DESCRIPTION
             "This object is used to specify the port."
     ::= { wwpLeosCfmLoopbackMsgEntry 1 }
 
 wwpLeosCfmLoopbackMsgTargetMEPID OBJECT-TYPE
     SYNTAX       Unsigned32 (1..8191)
     MAX-ACCESS   read-create
     STATUS       obsolete
     DESCRIPTION
             "This object is used to specify the MEPID.
              This object should only be set if wwpLeosCfmLoopbackMsgTargetMacAddr is not specified else 
              an error is returned."
     ::= { wwpLeosCfmLoopbackMsgEntry 2 }
     
 wwpLeosCfmLoopbackMsgTargetMacAddr OBJECT-TYPE
     SYNTAX       MacAddress
     MAX-ACCESS   read-create
     STATUS       obsolete
     DESCRIPTION
             "This object is used to specify the MacAddress to be used when sending link LoopbackMsg.
              This object should only be set if wwpLeosCfmLoopbackMsgTargetMEPID is not specified else 
              an error is returned."
     ::= { wwpLeosCfmLoopbackMsgEntry 3 }
     
 wwpLeosCfmLoopbackMsgCount OBJECT-TYPE
     SYNTAX       INTEGER (1..20) 
     MAX-ACCESS   read-create
     STATUS       obsolete
     DESCRIPTION
             "This object is used to specify the LoopbackMsg count to be used when sending link LoopbackMsg.
              "
     ::= { wwpLeosCfmLoopbackMsgEntry 4 }
 
 wwpLeosCfmLoopbackMsgData OBJECT-TYPE
     SYNTAX       DisplayString  (SIZE(1..127))
     MAX-ACCESS   read-create
     STATUS       obsolete
     DESCRIPTION                    
             "This object is used to specify the LoopbackMsg data to be used when sending link LoopbackMsg.
              "
     ::= { wwpLeosCfmLoopbackMsgEntry 5 }

 wwpLeosCfmLoopbackMsgPriority OBJECT-TYPE
     SYNTAX       INTEGER (0..7)
     MAX-ACCESS   read-create
     STATUS       obsolete
     DESCRIPTION
             "This object is used to specify the LoopbackMsg priority to be used when sending link LoopbackMsg.
              "
     ::= { wwpLeosCfmLoopbackMsgEntry 6 }
 
 wwpLeosCfmLoopbackMsgRowStatus OBJECT-TYPE
     SYNTAX       RowStatus
     MAX-ACCESS   read-create
     STATUS       obsolete
     DESCRIPTION
        "Used to manage the creation and deletion of the conceptual rows in this table.
	To create a row in this table, set this object to 'createAndGo'.
	To delete a row in this table, set this to 'destroy'."
     ::= { wwpLeosCfmLoopbackMsgEntry 7 }
 
 wwpLeosCfmLoopbackMsgDefaultInterval OBJECT-TYPE
     SYNTAX       INTEGER (10..60000)
     MAX-ACCESS   read-create
     STATUS       obsolete
     DESCRIPTION
             "The global default LoopbackMsg interval to be used when sending link LoopbackMsg
              "
     ::= { wwpLeosCfmLoopbackMsgEntry 8 }
     
 wwpLeosCfmLoopbackMsgDefaultTimeout OBJECT-TYPE
     SYNTAX       INTEGER (2000..10000)
     MAX-ACCESS   read-create
     STATUS       obsolete
     DESCRIPTION
             "The global default LoopbackMsg timeout to be used when sending link LoopbackMsg
              "
     ::= { wwpLeosCfmLoopbackMsgEntry 9 }

 
  --
  --  CFM Maintainence Domain Table 
  --                                   
 wwpLeosCfmMaintenanceDomainTable OBJECT-TYPE
     SYNTAX     SEQUENCE OF WwpLeosCfmMaintenanceDomainEntry
     MAX-ACCESS not-accessible
     STATUS     current
     DESCRIPTION
            "The (conceptual) table listing the configuration 
            parameters for the CFM Maintenance Domain Table."  
     ::= { wwpLeosCfmMaintenance 1 }
                
 wwpLeosCfmMaintenanceDomainEntry OBJECT-TYPE
     SYNTAX      WwpLeosCfmMaintenanceDomainEntry
     MAX-ACCESS  not-accessible
     STATUS      current
     DESCRIPTION
           "An entry (conceptual row) in the wwpLeosCfmMaintenanceDomainTable."
     INDEX {wwpLeosCfmMaintenanceDomainIndex }
     ::= { wwpLeosCfmMaintenanceDomainTable 1 }
                
 WwpLeosCfmMaintenanceDomainEntry ::=  SEQUENCE { 
     wwpLeosCfmMaintenanceDomainIndex                   Unsigned32,
     wwpLeosCfmMaintenanceDomainLevel                   INTEGER,
     wwpLeosCfmMaintenanceDomainName                    DisplayString,
     wwpLeosCfmMaintenanceDomainServiceCount            Unsigned32,
     wwpLeosCfmMaintenanceDomainMdFormat                Dot1agCfmMaintDomainNameType,
     wwpLeosCfmMaintenanceDomainMdName                  Dot1agCfmMaintDomainName,
     wwpLeosCfmMaintenanceDomainStatus                  RowStatus
 }
 
 wwpLeosCfmMaintenanceDomainIndex OBJECT-TYPE
     SYNTAX      Unsigned32
     MAX-ACCESS  read-only
     STATUS      current
     DESCRIPTION
             "This object specfies the unique index in the table."
     ::= { wwpLeosCfmMaintenanceDomainEntry 1 }
     
 wwpLeosCfmMaintenanceDomainLevel OBJECT-TYPE
     SYNTAX      INTEGER (0..7)
     MAX-ACCESS  read-write
     STATUS      current
     DESCRIPTION
             "This object specfies the domain level."
     ::= { wwpLeosCfmMaintenanceDomainEntry 2 }
 
 wwpLeosCfmMaintenanceDomainName OBJECT-TYPE
     SYNTAX      DisplayString (SIZE(1..43))
     MAX-ACCESS  read-write
     STATUS      current
     DESCRIPTION
             "The domain name which can be modified."
     ::= { wwpLeosCfmMaintenanceDomainEntry 3 }
  
 wwpLeosCfmMaintenanceDomainServiceCount OBJECT-TYPE
     SYNTAX      Unsigned32
     MAX-ACCESS  read-only
     STATUS      current
     DESCRIPTION
             "This object specifies number of CFM services mapped to this domain."
     ::= { wwpLeosCfmMaintenanceDomainEntry 4 }

 wwpLeosCfmMaintenanceDomainMdFormat OBJECT-TYPE
     SYNTAX      Dot1agCfmMaintDomainNameType
     MAX-ACCESS  read-write
     STATUS      current
     DESCRIPTION
             "The type (and thereby format) of the Maintenance Domain Name."
     REFERENCE
             "802.1ag clause 21.6.5.1"
     DEFVAL { charString }
     ::= { wwpLeosCfmMaintenanceDomainEntry 5 }

 wwpLeosCfmMaintenanceDomainMdName OBJECT-TYPE
     SYNTAX      Dot1agCfmMaintDomainName
     MAX-ACCESS  read-write
     STATUS      current
     DESCRIPTION
             "The Maintenance Domain name. The type/format of this object
              is determined by the value of the wwpLeosCfmMaintenanceDomainMdFormat object."
     REFERENCE
             "802.1ag clauses 3.24, 12.14.5, and 21.6.5.3"
        ::= { wwpLeosCfmMaintenanceDomainEntry 6 }

 wwpLeosCfmMaintenanceDomainStatus OBJECT-TYPE
     SYNTAX       RowStatus
     MAX-ACCESS   read-create
     STATUS       current
     DESCRIPTION
             "Used to manage the creation and deletion of the conceptual rows in this table.
             To create a row in this table, set this object to 'createAndGo'
             and specify, at a minimum, the wwpLeosCfmMaintenanceDomainLevel and
             wwpLeosCfmMaintenanceDomainName objects.
             During a create/set operation, if a non-default MdFormat is required, both the
             wwpLeosCfmMaintenanceDomainMdFormat and wwpLeosCfmMaintenanceDomainMdName objects
             must also be specified.
             To delete a row in this table, set this object to 'destroy'."
     ::= { wwpLeosCfmMaintenanceDomainEntry 7 }
                                                    
  --
  --  CFM MEP Table 
  --                                   
 wwpLeosCfmMEPTable OBJECT-TYPE
     SYNTAX     SEQUENCE OF WwpLeosCfmMEPEntry
     MAX-ACCESS not-accessible
     STATUS     obsolete
     DESCRIPTION
        "The (conceptual) table listing the configuration parameters for the CFM MEP table.
	This table is not supported on 39xx/51xx platforms, use wwpLeosCfmExtMEPEntry instead."
     ::= { wwpLeosCfmMEP 1 }
                
 wwpLeosCfmMEPEntry OBJECT-TYPE
     SYNTAX      WwpLeosCfmMEPEntry
     MAX-ACCESS  not-accessible
     STATUS      obsolete
     DESCRIPTION
           "An entry (conceptual row) in the wwpLeosCfmMEPTable."
     INDEX {wwpLeosCfmServiceIndex, wwpLeosCfmMEPPort}
     ::= { wwpLeosCfmMEPTable 1 }
                
 WwpLeosCfmMEPEntry ::=  SEQUENCE { 
     wwpLeosCfmMEPPort                                          INTEGER,        
     wwpLeosCfmMEPAdminState                                    INTEGER,        
     wwpLeosCfmMEPOperState                                     INTEGER,        
     wwpLeosCfmMEPDirection                                     INTEGER,
     wwpLeosCfmMEPCCMState            							INTEGER,
     wwpLeosCfmMEPCCMPriority         							INTEGER,
     wwpLeosCfmMEPLTMPriority         							INTEGER,  
     wwpLeosCfmMEPId											Unsigned32,
     wwpLeosCfmMEPMacAddr                                       MacAddress,
     wwpLeosCfmMEPNextLbmSeqNumber                              Counter32,
     wwpLeosCfmMEPRxValidInOrderLoopbackReply       			Counter32,
     wwpLeosCfmMEPRxValidOutOrderLoopbackReply          		Counter32,
     wwpLeosCfmMEPNextLTMSeqNumber                              Counter32,
     wwpLeosCfmMEPNumLoopbackRepliesTxmt                		Counter32,
     wwpLeosCfmMEPNumLTMReceived                                Counter32,
     wwpLeosCfmMEPNumLTMTxmt                                    Counter32,
     wwpLeosCfmMEPNumCCMTxmt                                    Counter32,     
     wwpLeosCfmMEPRowStatus                                     RowStatus,
     wwpLeosCfmMEPNumDMMSent									Counter32,
     wwpLeosCfmMEPDMMDelay										Counter32,
     wwpLeosCfmMEPDMMJitter										Counter32,
     wwpLeosCfmMEPNumLMMSent									Counter32,
     wwpLeosCfmMEPLMMFrameLossNear								Counter32,
     wwpLeosCfmMEPLMMFrameLossFar								Counter32,
     wwpLeosCfmMEPNumLMRReceived								Counter32,
     wwpLeosCfmMEPNumDMRReceived								Counter32,
     wwpLeosCfmMEPDMMMinDelay									Counter32,
     wwpLeosCfmMEPDMMMaxDelay									Counter32,
     wwpLeosCfmMEPDMMMinJitter									Counter32,
     wwpLeosCfmMEPDMMMaxJitter									Counter32,
     wwpLeosCfmMEPServiceName                                   DisplayString,
     wwpLeosCfmMEPSubPortName                                   DisplayString,
     wwpLeosCfmMEPVsPbtName                                     DisplayString,
     wwpLeosCfmMEPLogicalPortName                               DisplayString,
     wwpLeosCfmMEPSubPortIndex                                  Unsigned32,
     wwpLeosCfmMEPEncapsulation                                 INTEGER,
     wwpLeosCfmMEPLeadPortBayIndex                              Unsigned32,
     wwpLeosCfmMEPLeadPortShelfIndex                            Unsigned32,
     wwpLeosCfmMEPLeadPortModuleIndex                           Unsigned32,
     wwpLeosCfmMEPPBTBvid                                       Unsigned32,
     wwpLeosCfmMEPPBTEtype                                      Unsigned32,
     wwpLeosCfmMEPNumLbmTxmt                                    Counter32,
     wwpLeosCfmMEPNumLbmReceived                                Counter32,
     wwpLeosCfmMEPNumLoopbackRepliesReceived                    Counter32,
     wwpLeosCfmMEPNumLTRepliesTxmt                              Counter32,
     wwpLeosCfmMEPNumLTRepliesReceived                          Counter32,
     wwpLeosCfmMEPNumUnexpectedLTRepliesReceived                Counter32,
     wwpLeosCfmMEPNumCCMReceived                                Counter32
 }

 wwpLeosCfmMEPPort OBJECT-TYPE
     SYNTAX      INTEGER (1..65535)
     MAX-ACCESS  read-only
     STATUS      obsolete
     DESCRIPTION
             "This object specifies the MEP port id."
     ::= { wwpLeosCfmMEPEntry 1 }
 
 wwpLeosCfmMEPAdminState OBJECT-TYPE
     SYNTAX      INTEGER   {
                                disabled(1),
                                enabled(2)  
                          }
     MAX-ACCESS  read-write
     STATUS      obsolete
     DESCRIPTION
             "This object specifies the MEP admin state."
     ::= { wwpLeosCfmMEPEntry 2 }
 
 wwpLeosCfmMEPOperState OBJECT-TYPE
     SYNTAX      INTEGER   {
                                disabled(1),
                                enabled(2)  
                          }
     MAX-ACCESS  read-only
     STATUS      obsolete
     DESCRIPTION
             "This object is obsolete and should not be used."
     ::= { wwpLeosCfmMEPEntry 3 }
     
 wwpLeosCfmMEPDirection OBJECT-TYPE
     SYNTAX      INTEGER {
                                up(1),
                                down(2)
                         }
     MAX-ACCESS  read-create
     STATUS      obsolete
     DESCRIPTION
             "This object is used to specify the MEP direction of the service.
              This object can only be set if wwpLeosCfmServiceIndex is of type vlan."
     ::= { wwpLeosCfmMEPEntry 4 } 
 
 wwpLeosCfmMEPCCMState OBJECT-TYPE
     SYNTAX       INTEGER {
                                on(1),
                                off(2)
                                }
     MAX-ACCESS   read-write
     STATUS       obsolete
     DESCRIPTION
             "This object specifies the CCM transmission for the service specified by wwpLeosCfmServiceType."
     ::= { wwpLeosCfmMEPEntry 5 }
     
 wwpLeosCfmMEPCCMPriority OBJECT-TYPE
     SYNTAX       INTEGER (0..7)
     MAX-ACCESS   read-write
     STATUS       obsolete
     DESCRIPTION
             "This object specifies the priority of CCM messages transmitted."
     ::= { wwpLeosCfmMEPEntry 6 }
     
 wwpLeosCfmMEPLTMPriority OBJECT-TYPE
     SYNTAX      INTEGER (0..7)
     MAX-ACCESS  read-write
     STATUS      obsolete
     DESCRIPTION
             "This object specifies the priority received on the given service and port."
     ::= { wwpLeosCfmMEPEntry 7 }
 
 wwpLeosCfmMEPId OBJECT-TYPE
     SYNTAX      Unsigned32 (1..8191)
     MAX-ACCESS  read-create
     STATUS      obsolete
     DESCRIPTION
             "This object specifies the MEP id for the given service and port."
     ::= { wwpLeosCfmMEPEntry 8 }
     
 wwpLeosCfmMEPMacAddr OBJECT-TYPE
     SYNTAX      MacAddress
     MAX-ACCESS  read-only
     STATUS      obsolete
     DESCRIPTION
             "This object specifies the MAC address received on the given service and port.."
     ::= { wwpLeosCfmMEPEntry 9 }
     
 wwpLeosCfmMEPNextLbmSeqNumber OBJECT-TYPE
     SYNTAX      Counter32 
     MAX-ACCESS  read-only
     STATUS      obsolete
     DESCRIPTION
             "This object specifies the next lbm sequence number received on the given service and port."
     ::= { wwpLeosCfmMEPEntry 10 }
     
 wwpLeosCfmMEPRxValidInOrderLoopbackReply OBJECT-TYPE
     SYNTAX      Counter32
     MAX-ACCESS  read-only
     STATUS      obsolete
     DESCRIPTION
             "This object specifies the total valid in order loopback replies received on the given service and port."
     ::= { wwpLeosCfmMEPEntry 11 }
     
 wwpLeosCfmMEPRxValidOutOrderLoopbackReply OBJECT-TYPE
     SYNTAX      Counter32
     MAX-ACCESS  read-only
     STATUS      obsolete
     DESCRIPTION
             "This object specifies the total valid out of order loopback replies received on the given service and port."
     ::= { wwpLeosCfmMEPEntry 12 }
     
 wwpLeosCfmMEPNextLTMSeqNumber OBJECT-TYPE
     SYNTAX      Counter32 
     MAX-ACCESS  read-only
     STATUS      obsolete
     DESCRIPTION
             "This object specifies the next LTM serquence number received on the given service and port."
     ::= { wwpLeosCfmMEPEntry 13 }
     
 wwpLeosCfmMEPNumLoopbackRepliesTxmt OBJECT-TYPE
     SYNTAX      Counter32
     MAX-ACCESS  read-only
     STATUS      obsolete
     DESCRIPTION
             "This object specifies the flags total loopback replies transmitted on the given service and port."
     ::= { wwpLeosCfmMEPEntry 14 }
     
 wwpLeosCfmMEPNumLTMReceived OBJECT-TYPE
     SYNTAX      Counter32
     MAX-ACCESS  read-only
     STATUS      obsolete
     DESCRIPTION
             "This object specifies the total LTM messages received on the given service and port."
     ::= { wwpLeosCfmMEPEntry 15 }
     
 wwpLeosCfmMEPNumLTMTxmt OBJECT-TYPE
     SYNTAX      Counter32
     MAX-ACCESS  read-only
     STATUS      obsolete
     DESCRIPTION
             "This object specifies the total LTM transmitted on the given service and port."
     ::= { wwpLeosCfmMEPEntry 16 }
     
 wwpLeosCfmMEPNumCCMTxmt OBJECT-TYPE
     SYNTAX      Counter32
     MAX-ACCESS  read-only
     STATUS      obsolete
     DESCRIPTION
             "This object specifies the total CCM messages transmitted on the given service and port."
     ::= { wwpLeosCfmMEPEntry 17 }     
     
 wwpLeosCfmMEPRowStatus OBJECT-TYPE
     SYNTAX       RowStatus
     MAX-ACCESS   read-create
     STATUS       obsolete
     DESCRIPTION
       "Used to manage the creation and deletion of the conceptual rows in this table.
       To create a row in this table, set this object to 'createAndGo'.
       To delete a row in this table, set this to 'destroy'."
     ::= { wwpLeosCfmMEPEntry 18 }  
     
  wwpLeosCfmMEPNumDMMSent OBJECT-TYPE
     SYNTAX      Counter32
     MAX-ACCESS  read-only
     STATUS      obsolete
     DESCRIPTION
             "This object specifies the total delay measurement messages
             transmitted on the given service and port."
     ::= { wwpLeosCfmMEPEntry 19 } 
     
 wwpLeosCfmMEPDMMDelay OBJECT-TYPE
     SYNTAX      Counter32
     MAX-ACCESS  read-only
     STATUS      obsolete
     DESCRIPTION
             "This object specifies the average delay in microseconds
             measured during the last DMM performance test on the given service and port."
     ::= { wwpLeosCfmMEPEntry 20 } 
     
 wwpLeosCfmMEPDMMJitter OBJECT-TYPE
     SYNTAX      Counter32
     MAX-ACCESS  read-only
     STATUS      obsolete
     DESCRIPTION
             "This object specifies the average jitter in microseconds
             measured during the last DMM performance test on the given service and port."
     ::= { wwpLeosCfmMEPEntry 21 }
 
 wwpLeosCfmMEPNumLMMSent OBJECT-TYPE
     SYNTAX      Counter32
     MAX-ACCESS  read-only
     STATUS      obsolete
     DESCRIPTION
             "The total frame loss measurement messages transmitted
             during the last test performed on the given service and port."
     ::= { wwpLeosCfmMEPEntry 22 } 
     
 wwpLeosCfmMEPLMMFrameLossNear OBJECT-TYPE
     SYNTAX      Counter32
     MAX-ACCESS  read-only
     STATUS      obsolete
     DESCRIPTION
             "This object specifies the number of lost frames on the near side
             measured during the last LMM performance test on the given service and port."
     ::= { wwpLeosCfmMEPEntry 23 } 
     
 wwpLeosCfmMEPLMMFrameLossFar OBJECT-TYPE
     SYNTAX      Counter32
     MAX-ACCESS  read-only
     STATUS      obsolete
     DESCRIPTION
             "This object specifies the number of lost frames on the far side
             measured during the last LMM performance test on the given service and port."
     ::= { wwpLeosCfmMEPEntry 24 }
     
 wwpLeosCfmMEPNumLMRReceived OBJECT-TYPE
 	SYNTAX		Counter32
 	MAX-ACCESS	read-only
 	STATUS		obsolete
 	DESCRIPTION
 			"This object specifies the total number of frame loss measurement
 			replies received during the last test performed on the given service
 			and port.  If this count is zero, the near and far frame loss counts
 			are probably invalid as connectivity to the device being tested was
 			not available."
 	::= { wwpLeosCfmMEPEntry 25 }  
 	 
 wwpLeosCfmMEPNumDMRReceived OBJECT-TYPE
 	SYNTAX		Counter32
 	MAX-ACCESS	read-only
 	STATUS		obsolete
 	DESCRIPTION
 			"This object specifies the total number of delay measurement
 			replies received during the last test performed on the given service
 			and port.  If this count is not equal to the number of delay
 			measurement frames sent, the jitter and delay are probably invalid
 			as connectivity to the device being tested was not stable."
 	::= { wwpLeosCfmMEPEntry 26 }

 wwpLeosCfmMEPDMMMinDelay OBJECT-TYPE
     SYNTAX      Counter32
     MAX-ACCESS  read-only
     STATUS      obsolete
     DESCRIPTION
             "The minimum delay in microseconds measured during
             the last DMM performance test on the given service and port."
     ::= { wwpLeosCfmMEPEntry 27 }
      
 wwpLeosCfmMEPDMMMaxDelay OBJECT-TYPE
     SYNTAX      Counter32
     MAX-ACCESS  read-only
     STATUS      obsolete
     DESCRIPTION
             "The maximum delay in microseconds measured during
             the last DMM performance test on the given service and port."
     ::= { wwpLeosCfmMEPEntry 28 } 
     
 wwpLeosCfmMEPDMMMinJitter OBJECT-TYPE
     SYNTAX      Counter32
     MAX-ACCESS  read-only
     STATUS      obsolete
     DESCRIPTION
             "The minimum jitter in microseconds measured during
             the last DMM performance test on the given service and port."
     ::= { wwpLeosCfmMEPEntry 29 }

wwpLeosCfmMEPDMMMaxJitter OBJECT-TYPE
     SYNTAX      Counter32
     MAX-ACCESS  read-only
     STATUS      obsolete
     DESCRIPTION
             "The maximum jitter in microseconds measured during
             the last DMM performance test on the given service and port."
     ::= { wwpLeosCfmMEPEntry 30 }
 	
 wwpLeosCfmMEPServiceName OBJECT-TYPE
     SYNTAX      DisplayString (SIZE(0..41))
     MAX-ACCESS  read-only
     STATUS      obsolete
     DESCRIPTION
             "This object specifies the service name assigned to this port."
     ::= { wwpLeosCfmMEPEntry 50 }
  
 wwpLeosCfmMEPSubPortName OBJECT-TYPE
     SYNTAX      DisplayString (SIZE(0..31))
     MAX-ACCESS  read-only
     STATUS      obsolete
     DESCRIPTION
             "This object specifies the sub-port name assigned to the given service and port." 
     ::= { wwpLeosCfmMEPEntry 51 }

 wwpLeosCfmMEPVsPbtName OBJECT-TYPE
     SYNTAX      DisplayString (SIZE(0..31))
     MAX-ACCESS  read-only
     STATUS      obsolete
     DESCRIPTION
             "This object specifies the virtual switch or Pbt tunnel assigned to the given service and port." 
     ::= { wwpLeosCfmMEPEntry 52 }

 wwpLeosCfmMEPLogicalPortName OBJECT-TYPE
     SYNTAX      DisplayString (SIZE(0..31))
     MAX-ACCESS  read-only
     STATUS      obsolete
     DESCRIPTION
             "This object specifies the logical port name assigned to the given service and port." 
     ::= { wwpLeosCfmMEPEntry 53 }

 wwpLeosCfmMEPSubPortIndex OBJECT-TYPE
     SYNTAX      Unsigned32
     MAX-ACCESS  read-only
     STATUS      obsolete
     DESCRIPTION
             "This object specifies the CFM sub-port index."
     ::= { wwpLeosCfmMEPEntry 54 }

 wwpLeosCfmMEPEncapsulation OBJECT-TYPE
     SYNTAX      INTEGER {
                                ieee802dot1d(1),
                                pbtCfmEncap(2)
                         }
     MAX-ACCESS  read-only
     STATUS      obsolete
     DESCRIPTION
             "This object specifies the encapsulation applied to the service and port."
     ::= { wwpLeosCfmMEPEntry 55 } 
 
 wwpLeosCfmMEPLeadPortBayIndex OBJECT-TYPE
     SYNTAX          Unsigned32 (1..1)
     MAX-ACCESS      read-only
     STATUS          obsolete
     DESCRIPTION
           "This object specifies the agent bay the MEP is in."               
     ::= { wwpLeosCfmMEPEntry 56 }

 wwpLeosCfmMEPLeadPortShelfIndex OBJECT-TYPE
     SYNTAX          Unsigned32 (1..1)
     MAX-ACCESS      read-only
     STATUS          obsolete
     DESCRIPTION
           "This object specifies the agent shelf the MEP is in."               
     ::= { wwpLeosCfmMEPEntry 57 }

 wwpLeosCfmMEPLeadPortModuleIndex OBJECT-TYPE
     SYNTAX          Unsigned32 (1..7 | 255)
     MAX-ACCESS      read-only
     STATUS          obsolete
     DESCRIPTION
           "This object specifies the agent module the MEP is in.
            Index = 255 is reserved for Lag ports and this object cannot be set to 255
            in this table."               
     ::= { wwpLeosCfmMEPEntry 58 }
     
 wwpLeosCfmMEPPBTBvid OBJECT-TYPE
     SYNTAX          Unsigned32 (1..8191)
     MAX-ACCESS      read-only
     STATUS          obsolete
     DESCRIPTION
             "This object specifies the BVID assigned to the given service and port."
     ::= { wwpLeosCfmMEPEntry 59 }

 wwpLeosCfmMEPPBTEtype OBJECT-TYPE
     SYNTAX          Unsigned32 (1..8191)
     MAX-ACCESS      read-only
     STATUS          obsolete
     DESCRIPTION
             "This object specifies the E-type assigned to the given service and port."
     ::= { wwpLeosCfmMEPEntry 60 }

 wwpLeosCfmMEPNumLbmTxmt OBJECT-TYPE
     SYNTAX      Counter32
     MAX-ACCESS  read-only
     STATUS      obsolete
     DESCRIPTION
             "This object specifies the total loopback messages transmitted on the
              given service and port."
     ::= { wwpLeosCfmMEPEntry 61 }
     
 wwpLeosCfmMEPNumLbmReceived OBJECT-TYPE
     SYNTAX      Counter32
     MAX-ACCESS  read-only
     STATUS      obsolete
     DESCRIPTION
             "This object specifies the total loopback messages received on the
              given service and port."
     ::= { wwpLeosCfmMEPEntry 62 }

 wwpLeosCfmMEPNumLoopbackRepliesReceived OBJECT-TYPE
     SYNTAX      Counter32
     MAX-ACCESS  read-only
     STATUS      obsolete
     DESCRIPTION
             "This object specifies the total loopback replies received on the
              given service and port."
     ::= { wwpLeosCfmMEPEntry 63 }

 wwpLeosCfmMEPNumLTRepliesTxmt OBJECT-TYPE
     SYNTAX      Counter32
     MAX-ACCESS  read-only
     STATUS      obsolete
     DESCRIPTION
             "This object specifies the total link trace replies transmitted on the
              given service and port."
     ::= { wwpLeosCfmMEPEntry 64 }

 wwpLeosCfmMEPNumLTRepliesReceived OBJECT-TYPE
     SYNTAX      Counter32
     MAX-ACCESS  read-only
     STATUS      obsolete
     DESCRIPTION
             "This object specifies the total link trace replies received on the
              given service and port."
     ::= { wwpLeosCfmMEPEntry 65 }

 wwpLeosCfmMEPNumUnexpectedLTRepliesReceived OBJECT-TYPE
     SYNTAX      Counter32
     MAX-ACCESS  read-only
     STATUS      obsolete
     DESCRIPTION
             "This object specifies the total unexpected link trace replies received on the
              given service and port."
     ::= { wwpLeosCfmMEPEntry 66 }

 wwpLeosCfmMEPNumCCMReceived OBJECT-TYPE
     SYNTAX      Counter32
     MAX-ACCESS  read-only
     STATUS      obsolete
     DESCRIPTION
             "This object specifies the total CCM messages received on the given service and port."
     ::= { wwpLeosCfmMEPEntry 67 }

  --
  --  CFM Remote MEP Table
  --                                   
 wwpLeosCfmRemoteMEPTable OBJECT-TYPE
     SYNTAX     SEQUENCE OF WwpLeosCfmRemoteMEPEntry
     MAX-ACCESS not-accessible
     STATUS     current
     DESCRIPTION
            "The (conceptual) table listing the display
             parameters for the Remote MEP table."
     ::= { wwpLeosCfmRemoteMEP 1 }
                
 wwpLeosCfmRemoteMEPEntry OBJECT-TYPE
     SYNTAX      WwpLeosCfmRemoteMEPEntry
     MAX-ACCESS  not-accessible
     STATUS      current
     DESCRIPTION
           "An entry (conceptual row) in the wwpLeosCfmRemoteMEPTable."
     INDEX {wwpLeosCfmServiceIndex, wwpLeosCfmRemoteMEPID}
     ::= { wwpLeosCfmRemoteMEPTable 1 }
                
 WwpLeosCfmRemoteMEPEntry ::=  SEQUENCE { 
     wwpLeosCfmRemoteMEPID                              Unsigned32,
     wwpLeosCfmRemoteMEPAdminState                  	INTEGER,     
     wwpLeosCfmRemoteMEPOperState                       INTEGER,
     wwpLeosCfmRemoteMEPTime                            TimeTicks,
     wwpLeosCfmRemoteMEPMacAddr                         MacAddress,
     wwpLeosCfmRemoteMEPKLastMacStatus      		TruthValue,
     wwpLeosCfmRemoteMEPFailureFlag                     TruthValue,
     wwpLeosCfmRemoteMEPCCMErrorFlag            	TruthValue,
     wwpLeosCfmRemoteMEPRDIErrorFlag            	TruthValue,
     wwpLeosCfmRemoteMEPNumCCMRx         		Counter32,
     wwpLeosCfmRemoteMEPNumDMMSent			Counter32,
     wwpLeosCfmRemoteMEPDelay				Counter32,
     wwpLeosCfmRemoteMEPJitter				Counter32,
     wwpLeosCfmRemoteMEPNumLMMSent			Counter32,
     wwpLeosCfmRemoteMEPFrameLossNear			Counter32,
     wwpLeosCfmRemoteMEPFrameLossFar			Counter32,
     wwpLeosCfmRemoteMEPNumLMRReceived			Counter32,
     wwpLeosCfmRemoteMEPNumCCMLost			Counter32,
     wwpLeosCfmRemoteMEPNumDMRReceived			Counter32, 
     wwpLeosCfmRemoteMEPHoldState			INTEGER,   --deprecated
     wwpLeosCfmRemoteMEPCCMComment			DisplayString,   
     wwpLeosCfmRemoteMEPBadSequence                     Counter32,
     wwpLeosCfmRemoteMEPMinDelay			Counter32,
     wwpLeosCfmRemoteMEPMaxDelay			Counter32,
     wwpLeosCfmRemoteMEPMinJitter			Counter32,
     wwpLeosCfmRemoteMEPMaxJitter			Counter32,
     wwpLeosCfmRemoteMEPSubPortName                     DisplayString,
     wwpLeosCfmRemoteMEPServiceName                     DisplayString,
     wwpLeosCfmRemoteMEPBayIndex                        Unsigned32,
     wwpLeosCfmRemoteMEPShelfIndex                      Unsigned32,
     wwpLeosCfmRemoteMEPModuleIndex                     Unsigned32,
     wwpLeosCfmRemoteMEPPreviousBayIndex                Unsigned32,
     wwpLeosCfmRemoteMEPPreviousShelfIndex              Unsigned32,
     wwpLeosCfmRemoteMEPPreviousModuleIndex             Unsigned32,
     wwpLeosCfmRemoteMEPLastPortStatus                  INTEGER,
     wwpLeosCfmRemoteMEPLastInterfaceStatus             INTEGER,
     wwpLeosCfmRemoteMEPLastSeqNum                      Unsigned32,
     wwpLeosCfmRemoteMEPCCMSeqErrors                    Unsigned32,
     wwpLeosCfmRemoteMEPCCMLevel                        INTEGER,
     wwpLeosCfmRemoteCfmMEPHoldState                    INTEGER,
     wwpLeosCfmRemoteMEPServiceClear                    TruthValue,
     wwpLeosCfmRemoteMEPServiceStatisticsClear          TruthValue,  
     wwpLeosCfmRemoteMEPAccelerated			TruthValue,
     wwpLeosCfmRemoteMEPRowStatus                       RowStatus,
     wwpLeosCfmRemoteMEPNumSLMSent			Counter32,
     wwpLeosCfmRemoteMEPSLMFrameLossNear		Integer32,
     wwpLeosCfmRemoteMEPSLMFrameLossFar			Integer32,
     wwpLeosCfmRemoteMEPNumSLRReceived			Counter32,
     wwpLeosCfmRemoteMEPCvid                            INTEGER
 }

 wwpLeosCfmRemoteMEPID OBJECT-TYPE
     SYNTAX      Unsigned32 (1..8191)
     MAX-ACCESS  read-only
     STATUS      current
     DESCRIPTION
             "This object specifies the remote MEPID."
     ::= { wwpLeosCfmRemoteMEPEntry 1 }
  
  wwpLeosCfmRemoteMEPAdminState OBJECT-TYPE
     SYNTAX      INTEGER  {
                                disabled(1),
                                enabled(2)
                          }
     MAX-ACCESS  read-write
     STATUS      current
     DESCRIPTION
             "This object specifies the administrative state of the Remote MEP State Machine."
     ::= { wwpLeosCfmRemoteMEPEntry 2 }
     
  wwpLeosCfmRemoteMEPOperState OBJECT-TYPE
     SYNTAX      INTEGER  {
                                disabled(1),
                                enabled(2),
                                hold(3),
                                holdLocked(4)
                          }
     MAX-ACCESS  read-only
     STATUS      current
     DESCRIPTION
             "The object specifies the operational state of the Remote MEP State Machine.
             A 'disabled' state means the remote mep is admin disabled.
             An 'enabled' state means the remote mep is operationally enabled.
             A 'hold' state means the remote mep is admin enabled but currently in operational hold state.
             A 'holdLocked' state means the remote mep is locked in hold state."
     ::= { wwpLeosCfmRemoteMEPEntry 3 }
  
 wwpLeosCfmRemoteMEPTime OBJECT-TYPE
     SYNTAX      TimeTicks 
     MAX-ACCESS  read-only
     STATUS      current
     DESCRIPTION
             "This object specifies the time at which the Remote MEP State Machine last
              entered RMEP_FAILED or RMEP_OK states."
     ::= { wwpLeosCfmRemoteMEPEntry 4 }
 
 wwpLeosCfmRemoteMEPMacAddr OBJECT-TYPE
     SYNTAX      MacAddress 
     MAX-ACCESS  read-create
     STATUS      current
     DESCRIPTION
             "This object specifies the MAC address of the remote MEP."
     ::= { wwpLeosCfmRemoteMEPEntry 5 }
 
 wwpLeosCfmRemoteMEPKLastMacStatus OBJECT-TYPE
     SYNTAX      TruthValue 
     MAX-ACCESS  read-only
     STATUS      current
     DESCRIPTION
             "This object specifies the last MAC status received."
     ::= { wwpLeosCfmRemoteMEPEntry 6 }
 
 wwpLeosCfmRemoteMEPFailureFlag OBJECT-TYPE
     SYNTAX      TruthValue 
     MAX-ACCESS  read-only
     STATUS      current
     DESCRIPTION
             "This object specifies the Remote MEP failure flag."
     ::= { wwpLeosCfmRemoteMEPEntry  7 }
 
 wwpLeosCfmRemoteMEPCCMErrorFlag OBJECT-TYPE
     SYNTAX      TruthValue 
     MAX-ACCESS  read-only
     STATUS      current
     DESCRIPTION
             "This object specifies the MEP CCM error flag."
     ::= { wwpLeosCfmRemoteMEPEntry 8 }
 
 wwpLeosCfmRemoteMEPRDIErrorFlag OBJECT-TYPE
     SYNTAX      TruthValue 
     MAX-ACCESS  read-only
     STATUS      current
     DESCRIPTION
             "This object specifies the MEP RDI error flag."
     ::= { wwpLeosCfmRemoteMEPEntry 9 }
 
 wwpLeosCfmRemoteMEPNumCCMRx     OBJECT-TYPE
     SYNTAX      Counter32
     MAX-ACCESS  read-only
     STATUS      current
     DESCRIPTION
             "This object is used to show the number of MEP CCM frames received."
     ::= { wwpLeosCfmRemoteMEPEntry 10 }  
     
 wwpLeosCfmRemoteMEPNumDMMSent	OBJECT-TYPE
 	SYNTAX		Counter32
 	MAX-ACCESS	read-only
 	STATUS		current
 	DESCRIPTION
 	      "The number of DMM frames sent."
 	::= { wwpLeosCfmRemoteMEPEntry 11 }
 	
 wwpLeosCfmRemoteMEPDelay		OBJECT-TYPE
	SYNTAX		Counter32
 	MAX-ACCESS	read-only
 	STATUS		current
 	DESCRIPTION
 			"This object is used to show the average Delay in microseconds
 			during the last Delay Measurement test."
    ::= { wwpLeosCfmRemoteMEPEntry 12 }
 
 wwpLeosCfmRemoteMEPJitter		OBJECT-TYPE
	SYNTAX		Counter32
 	MAX-ACCESS	read-only
 	STATUS		current
 	DESCRIPTION
 			"This object is used to show the average Jitter in microseconds
 			during the last Delay Measurement test."
    ::= { wwpLeosCfmRemoteMEPEntry 13 }

 wwpLeosCfmRemoteMEPNumLMMSent	OBJECT-TYPE
 	SYNTAX		Counter32
 	MAX-ACCESS	read-only
 	STATUS		current
 	DESCRIPTION
 			"This object is used to show the number of LMM frames sent."
    ::= { wwpLeosCfmRemoteMEPEntry 14 }
 	
 wwpLeosCfmRemoteMEPFrameLossNear	OBJECT-TYPE
	SYNTAX		Counter32
 	MAX-ACCESS	read-only
 	STATUS		current
 	DESCRIPTION
 			"This object is used to show the near side Frame Loss
 			during the last Frame Loss Measurement test."
    ::= { wwpLeosCfmRemoteMEPEntry 15 }
 
 wwpLeosCfmRemoteMEPFrameLossFar	OBJECT-TYPE
	SYNTAX		Counter32
 	MAX-ACCESS	read-only
 	STATUS		current
 	DESCRIPTION
 			"This object is used to show the far side Frame Loss
 			during the last Frame Loss Measurement test."
    ::= { wwpLeosCfmRemoteMEPEntry 16 }
 
 wwpLeosCfmRemoteMEPNumLMRReceived	OBJECT-TYPE
 	SYNTAX		Counter32
 	MAX-ACCESS	read-only
 	STATUS		current
 	DESCRIPTION
 			"This object is used to show the number of LMR frames received."
 	::= { wwpLeosCfmRemoteMEPEntry 17 }
 	
 wwpLeosCfmRemoteMEPNumCCMLost     OBJECT-TYPE
     SYNTAX      Counter32
     MAX-ACCESS  read-only
     STATUS      current
     DESCRIPTION
             "This object is used to show the number of MEP CCM frames lost,
             as calculated by watching for CCM sequence errors."
     ::= { wwpLeosCfmRemoteMEPEntry 18 }
       
 wwpLeosCfmRemoteMEPNumDMRReceived	OBJECT-TYPE
 	SYNTAX		Counter32
 	MAX-ACCESS	read-only
 	STATUS		current
 	DESCRIPTION
 			"This object specifies the number of DMR frames received."
 	::= { wwpLeosCfmRemoteMEPEntry 19 }

--deprecated
wwpLeosCfmRemoteMEPHoldState OBJECT-TYPE
    SYNTAX INTEGER
    		{ 
    		disabled(1),
    		enabled(2),
    		locked(3)
    		}
    MAX-ACCESS read-create
    STATUS deprecated
    DESCRIPTION
    	"This object is used to set the remote MEP Hold State"
    ::= { wwpLeosCfmRemoteMEPEntry 20 }
 
 wwpLeosCfmRemoteMEPRowStatus 	OBJECT-TYPE
   SYNTAX RowStatus
   MAX-ACCESS read-create
   STATUS current
   DESCRIPTION
   		"This object is used to create entries in remote mep table"
   ::= { wwpLeosCfmRemoteMEPEntry 21 } 
 
 wwpLeosCfmRemoteMEPCCMComment OBJECT-TYPE
    SYNTAX       DisplayString (SIZE(1..32))
    MAX-ACCESS   read-only
    STATUS       current
    DESCRIPTION
             "This mib object contains the CCM Comment, if available,
             that was sent by the remote Ciena device."
     ::= { wwpLeosCfmRemoteMEPEntry 22 }
     
 wwpLeosCfmRemoteMEPBadSequence OBJECT-TYPE
    SYNTAX       Counter32
    MAX-ACCESS   read-only
    STATUS       current
    DESCRIPTION
             "This mib object contains the number of LMR frames received 
              with bad sequence number, for a given service and remote mep."
     ::= { wwpLeosCfmRemoteMEPEntry 23 }
  	
 wwpLeosCfmRemoteMEPMinDelay		OBJECT-TYPE
	SYNTAX		Counter32
 	MAX-ACCESS	read-only
 	STATUS		current
 	DESCRIPTION
 		"The minimum Delay in microseconds
 		during the last Delay Measurement test."
 	::= { wwpLeosCfmRemoteMEPEntry 24 }
 	
 wwpLeosCfmRemoteMEPMaxDelay		OBJECT-TYPE
	SYNTAX		Counter32
 	MAX-ACCESS	read-only
 	STATUS		current
 	DESCRIPTION
 		"The maximum Delay in microseconds
 		during the last Delay Measurement test."
 	::= { wwpLeosCfmRemoteMEPEntry 25 }
 
 wwpLeosCfmRemoteMEPMinJitter		OBJECT-TYPE
	SYNTAX		Counter32
 	MAX-ACCESS	read-only
 	STATUS		current
 	DESCRIPTION
 		"The minimum jitter in microseconds
 		during the last Delay Measurement test."
 	::= { wwpLeosCfmRemoteMEPEntry 26 }
 
 wwpLeosCfmRemoteMEPMaxJitter		OBJECT-TYPE
	SYNTAX		Counter32
 	MAX-ACCESS	read-only
 	STATUS		current
 	DESCRIPTION
 		"The maximum jitter in microseconds
 		during the last Delay Measurement test."
 	::= { wwpLeosCfmRemoteMEPEntry 27 }
 
 wwpLeosCfmRemoteCfmMEPHoldState OBJECT-TYPE
     SYNTAX      INTEGER  {
                                disable(1),
                                enable(2),
                                lock(3)
                                }
     MAX-ACCESS  read-create
     STATUS      current
     DESCRIPTION
             "Hold-state for the remote-mep entry."
     ::= { wwpLeosCfmRemoteMEPEntry 28 }
 
  wwpLeosCfmRemoteMEPServiceClear OBJECT-TYPE
     SYNTAX      TruthValue
     MAX-ACCESS  read-create
     STATUS      current
     DESCRIPTION
             "Setting this object to true causes the remote MEP for this service
              to be re-initialized ."
     ::= { wwpLeosCfmRemoteMEPEntry 29 }
  
  wwpLeosCfmRemoteMEPServiceStatisticsClear OBJECT-TYPE
     SYNTAX      TruthValue
     MAX-ACCESS  read-create
     STATUS      current
     DESCRIPTION
             "Setting this object to true resets the statistics for the remote MEP
              for this service."
     ::= { wwpLeosCfmRemoteMEPEntry 30 }
 
  wwpLeosCfmRemoteMEPAccelerated OBJECT-TYPE
     SYNTAX      TruthValue
     MAX-ACCESS  read-only
     STATUS      current
     DESCRIPTION
             "Specifies if the remote-mep is monitored in the hardware."
     ::= { wwpLeosCfmRemoteMEPEntry 49 }
                                 
 wwpLeosCfmRemoteMEPSubPortName   OBJECT-TYPE
     SYNTAX          DisplayString (SIZE(0..31))
     MAX-ACCESS      read-only
     STATUS          current
     DESCRIPTION
           "This object indicates the unique index for the module."               
     ::= { wwpLeosCfmRemoteMEPEntry 50 }

 wwpLeosCfmRemoteMEPServiceName OBJECT-TYPE
     SYNTAX      DisplayString (SIZE(0..41))
     MAX-ACCESS  read-only
     STATUS      current
     DESCRIPTION
             "This object specifies the Service name."
     ::= { wwpLeosCfmRemoteMEPEntry 51 }
  
 wwpLeosCfmRemoteMEPBayIndex          OBJECT-TYPE
     SYNTAX          Unsigned32 (1..1)
     MAX-ACCESS      read-only
     STATUS          current
     DESCRIPTION
           "This object specifies the agent bay the MEP is in."               
     ::= { wwpLeosCfmRemoteMEPEntry 52 }

 wwpLeosCfmRemoteMEPShelfIndex          OBJECT-TYPE
     SYNTAX          Unsigned32 (1..1)
     MAX-ACCESS      read-only
     STATUS          current
     DESCRIPTION
           "This object specifies the agent shelf the MEP is in."               
     ::= { wwpLeosCfmRemoteMEPEntry 53 }

 wwpLeosCfmRemoteMEPModuleIndex          OBJECT-TYPE
     SYNTAX          Unsigned32 (1..7 | 255)
     MAX-ACCESS      read-only
     STATUS          current
     DESCRIPTION
           "This object specifies the agent module the MEP is in.
            Index = 255 is reserved for Lag ports and this object cannot be set to 255
            in this table."               
     ::= { wwpLeosCfmRemoteMEPEntry 54 }
     
 wwpLeosCfmRemoteMEPPreviousBayIndex    OBJECT-TYPE
     SYNTAX          Unsigned32 (1..1)
     MAX-ACCESS      read-only
     STATUS          current
     DESCRIPTION
           "This object specifies the agent bay the MEP was previously in."               
     ::= { wwpLeosCfmRemoteMEPEntry 55 }
     
 wwpLeosCfmRemoteMEPPreviousShelfIndex  OBJECT-TYPE
     SYNTAX          Unsigned32 (1..1)
     MAX-ACCESS      read-only
     STATUS          current
     DESCRIPTION
           "This object specifies the agent shelf the MEP was previously in."               
     ::= { wwpLeosCfmRemoteMEPEntry 56 }

 wwpLeosCfmRemoteMEPPreviousModuleIndex  OBJECT-TYPE
     SYNTAX          Unsigned32 (1..7 | 255)
     MAX-ACCESS      read-only
     STATUS          current
     DESCRIPTION
           "This object specifies the agent module the MEP was previously in.
            Index = 255 is reserved for Lag ports and this object cannot be set to 255
            in this table."               
     ::= { wwpLeosCfmRemoteMEPEntry 57 }
          
 wwpLeosCfmRemoteMEPLastPortStatus OBJECT-TYPE
     SYNTAX      INTEGER {
                   unknown(1),
                   none(2),
                   blocked(3),
                   up(4)
                 }
     MAX-ACCESS  read-only
     STATUS      current
     DESCRIPTION
             "This object specifies the remote MEP last port status."
     ::= { wwpLeosCfmRemoteMEPEntry 58 }

 wwpLeosCfmRemoteMEPLastInterfaceStatus OBJECT-TYPE
     SYNTAX      INTEGER {
                   none(1),
                   up(2),
                   down(3),
                   testing(4),
                   dormant(5),
                   lowerLayerDown(6),
                   notPresent(7)
                 }
     MAX-ACCESS  read-only
     STATUS      current
     DESCRIPTION
             "This object specifies the remote MEP interface status."
     ::= { wwpLeosCfmRemoteMEPEntry 59 }

 wwpLeosCfmRemoteMEPLastSeqNum     OBJECT-TYPE
     SYNTAX      Unsigned32
     MAX-ACCESS  read-only
     STATUS      current
     DESCRIPTION
             "This object is used to show the last sequence number of the remote MEP."
     ::= { wwpLeosCfmRemoteMEPEntry 60 }

 wwpLeosCfmRemoteMEPCCMSeqErrors     OBJECT-TYPE
     SYNTAX      Unsigned32
     MAX-ACCESS  read-only
     STATUS      current
     DESCRIPTION
             "This object is used to show the number of MEP CCM frames sequence errors."
     ::= { wwpLeosCfmRemoteMEPEntry 61 }

 wwpLeosCfmRemoteMEPCCMLevel OBJECT-TYPE
     SYNTAX      INTEGER (1..256)
     MAX-ACCESS  read-only
     STATUS      current
     DESCRIPTION
             "This object specifies the CCM level."
     ::= { wwpLeosCfmRemoteMEPEntry 62 } 
     
  --OID 63 is deprecated in 5305 MIB, OID 64 is removed in the 5305 MIB
  wwpLeosCfmRemoteMEPDeleteAll OBJECT-TYPE
     SYNTAX      TruthValue 
     MAX-ACCESS  read-write
     STATUS      current
     DESCRIPTION
             "Setting this object to true deletes all remote meps.
              This object always returns false."
     ::= { wwpLeosCfmRemoteMEP 65 }  
     
  wwpLeosCfmRemoteMEPNumSLMSent	OBJECT-TYPE
 	SYNTAX		Counter32
 	MAX-ACCESS	read-only
 	STATUS		current
 	DESCRIPTION
 			"This object is used to show the number of SLM frames sent."
    ::= { wwpLeosCfmRemoteMEPEntry 66 }
 	
 wwpLeosCfmRemoteMEPSLMFrameLossNear	OBJECT-TYPE
	SYNTAX		Integer32
 	MAX-ACCESS	read-only
 	STATUS		current
 	DESCRIPTION
 			"This object is used to show the near side Frame Loss
 			during the last Synthetic Loss Measurement test."
    ::= { wwpLeosCfmRemoteMEPEntry 67 }
 
 wwpLeosCfmRemoteMEPSLMFrameLossFar	OBJECT-TYPE
	SYNTAX		Integer32
 	MAX-ACCESS	read-only
 	STATUS		current
 	DESCRIPTION
 			"This object is used to show the far side Frame Loss
 			during the last Synthetic Loss Measurement test."
    ::= { wwpLeosCfmRemoteMEPEntry 68 }
 
 wwpLeosCfmRemoteMEPNumSLRReceived	OBJECT-TYPE
 	SYNTAX		Counter32
 	MAX-ACCESS	read-only
 	STATUS		current
 	DESCRIPTION
 			"This object is used to show the number of SLR frames received."
 	::= { wwpLeosCfmRemoteMEPEntry 69 }

 wwpLeosCfmRemoteMEPCvid OBJECT-TYPE
 	 SYNTAX		INTEGER ( 0..4095)
 	 MAX-ACCESS     read-write
 	 STATUS		current
 	 DESCRIPTION
 	                "This object specifies the Customer VLAN ID for the Remote MEP."
 	 ::= { wwpLeosCfmRemoteMEPEntry	70 }

  
  --
  --  CFM Port Stack Table
  --                                   
 wwpLeosCfmPortStackTable OBJECT-TYPE
     SYNTAX     SEQUENCE OF WwpLeosCfmPortStackEntry
     MAX-ACCESS not-accessible
     STATUS     deprecated
     DESCRIPTION
            "The (conceptual) table listing the display 
             parameters for the CFM port stack table."  
     ::= { wwpLeosCfmStack 1 }
                
 wwpLeosCfmPortStackEntry OBJECT-TYPE
     SYNTAX      WwpLeosCfmPortStackEntry
     MAX-ACCESS  not-accessible
     STATUS      deprecated
     DESCRIPTION
           "An entry (conceptual row) in the wwpLeosCfmPortStackTable."
     INDEX {wwpLeosCfmPortStackPort, wwpLeosCfmPortStackVid, wwpLeosCfmPortStackType, wwpLeosCfmPortStackLevel}
     ::= { wwpLeosCfmPortStackTable 1 }
                
 WwpLeosCfmPortStackEntry ::=  SEQUENCE {
     wwpLeosCfmPortStackPort        INTEGER, 
     wwpLeosCfmPortStackVid         INTEGER, 
     wwpLeosCfmPortStackType        INTEGER,
     wwpLeosCfmPortStackLevel       Unsigned32,
     wwpLeosCfmPortStackMEPId       INTEGER
 }
 
 wwpLeosCfmPortStackPort OBJECT-TYPE
     SYNTAX      INTEGER (1..65535)
     MAX-ACCESS  read-only
     STATUS      deprecated
     DESCRIPTION
             "This object is the index in the table used to specify the port id."
     ::= { wwpLeosCfmPortStackEntry 1 }

 wwpLeosCfmPortStackVid OBJECT-TYPE
     SYNTAX      INTEGER (1..24576)
     MAX-ACCESS  read-only
     STATUS      deprecated
     DESCRIPTION
             "This object is the index in the table used to show the VLAN."
     ::= { wwpLeosCfmPortStackEntry 2 }

 wwpLeosCfmPortStackType OBJECT-TYPE
     SYNTAX      INTEGER  {
                                        mepUp(1),
                                        mepDown(2),
                                        mip(3)
                                }
     MAX-ACCESS  read-only
     STATUS      deprecated
     DESCRIPTION
             "This object is the index in the table used to show the type of Maintenance Point."
     ::= { wwpLeosCfmPortStackEntry 3 }
                          
  wwpLeosCfmPortStackLevel OBJECT-TYPE
     SYNTAX      Unsigned32 (0..7)
     MAX-ACCESS  read-only
     STATUS      deprecated
     DESCRIPTION
             "This object is the index in the table and is used to show the level of stack."
     ::= { wwpLeosCfmPortStackEntry 4 }

   wwpLeosCfmPortStackMEPId OBJECT-TYPE
     SYNTAX      INTEGER (1..100)
     MAX-ACCESS  read-only
     STATUS      deprecated
     DESCRIPTION
             "The MEP ID."
     ::= { wwpLeosCfmPortStackEntry 5 }
 
  --
  --  CFM Port Stack Table
  --                                   
 wwpLeosCfmExtPortStackTable OBJECT-TYPE
     SYNTAX     SEQUENCE OF WwpLeosCfmExtPortStackEntry
     MAX-ACCESS not-accessible
     STATUS     current
     DESCRIPTION
            "The (conceptual) table listing the display 
             parameters for the CFM port stack table."  
     ::= { wwpLeosCfmExtStack 1 } 
     
 wwpLeosCfmExtPortStackEntry OBJECT-TYPE
     SYNTAX      WwpLeosCfmExtPortStackEntry
     MAX-ACCESS  not-accessible
     STATUS      current
     DESCRIPTION
           "An entry (conceptual row) in the wwpLeosCfmPortStackTable."
     INDEX {wwpLeosCfmExtPortStackVid, wwpLeosCfmExtPortStackPort, wwpLeosCfmExtPortStackType, wwpLeosCfmExtPortStackLevel}
     ::= { wwpLeosCfmExtPortStackTable 1 } 
     
 WwpLeosCfmExtPortStackEntry ::=  SEQUENCE {
     wwpLeosCfmExtPortStackVid         INTEGER, 
	 wwpLeosCfmExtPortStackPort        INTEGER, 
     wwpLeosCfmExtPortStackType        INTEGER,
     wwpLeosCfmExtPortStackLevel       Unsigned32,
     wwpLeosCfmExtPortStackMEPId       INTEGER
 }
 wwpLeosCfmExtPortStackVid OBJECT-TYPE
     SYNTAX      INTEGER (1..24576)
     MAX-ACCESS  read-only
     STATUS      current
     DESCRIPTION
             "This object is the index in the table and is used to show the VLAN."
     ::= { wwpLeosCfmExtPortStackEntry 1 }
     
  wwpLeosCfmExtPortStackPort OBJECT-TYPE
     SYNTAX      INTEGER (1..65535)
     MAX-ACCESS  read-only
     STATUS      current
     DESCRIPTION
             "This object is used as index in the table and specifies the port id."
     ::= { wwpLeosCfmExtPortStackEntry 2 } 
     
 wwpLeosCfmExtPortStackType OBJECT-TYPE
     SYNTAX      INTEGER  {
                                        mepUp(1),
                                        mepDown(2),
                                        mip(3)
                                }
     MAX-ACCESS  read-only
     STATUS      current
     DESCRIPTION
             "This object is used as index in the table and is used to show the type of Maintenance Point."
     ::= { wwpLeosCfmExtPortStackEntry 3 }    
     
  wwpLeosCfmExtPortStackLevel OBJECT-TYPE
     SYNTAX      Unsigned32 (0..7)
     MAX-ACCESS  read-only
     STATUS      current
     DESCRIPTION
             "This object is used as index in the table and is used to show the level of stack."
     ::= { wwpLeosCfmExtPortStackEntry 4 }
     
   wwpLeosCfmExtPortStackMEPId OBJECT-TYPE
     SYNTAX      INTEGER (1..100)
     MAX-ACCESS  read-only
     STATUS      current
     DESCRIPTION
             "The MEP ID."
     ::= { wwpLeosCfmExtPortStackEntry 5 }
 
  --
  --  CFM Mip CCM Db Table
  --                                   
 wwpLeosCfmMipCCMDbTable OBJECT-TYPE
     SYNTAX     SEQUENCE OF WwpLeosCfmMipCCMDbEntry
     MAX-ACCESS not-accessible
     STATUS     current
     DESCRIPTION
            "The (conceptual) table listing the display 
             parameters for the MIP CCM Db table."  
     ::= { wwpLeosCfmMipCCMDb 1 }
                
 wwpLeosCfmMipCCMDbEntry OBJECT-TYPE
     SYNTAX      WwpLeosCfmMipCCMDbEntry
     MAX-ACCESS  not-accessible
     STATUS      current
     DESCRIPTION
           "An entry (conceptual row) in the wwpLeosCfmMipCCMDbTable."
     INDEX { wwpLeosCfmMipCCMDbIndex }
     ::= { wwpLeosCfmMipCCMDbTable 1 }
                
 WwpLeosCfmMipCCMDbEntry ::=  SEQUENCE {                      
        wwpLeosCfmMipCCMDbIndex                           Unsigned32,
        wwpLeosCfmMipCCMDbVid                             Unsigned32,
        wwpLeosCfmMipCCMDbMacAddr                         MacAddress,
        wwpLeosCfmMipCCMDbPort                            INTEGER,
        wwpLeosCfmMipCCMDbMEPID                           INTEGER,
        wwpLeosCfmMipCCMdbNumCCMRx                        Counter32,
        wwpLeosCfmMipCCMDbTime                            TimeTicks,
        wwpLeosCfmMipCCMDbLastMacStatus                   TruthValue,
        wwpLeosCfmMipCCMDbRDIErrorFlag                    TruthValue
 }                                    
 
 wwpLeosCfmMipCCMDbIndex OBJECT-TYPE
     SYNTAX      Unsigned32 (1..24576)
     MAX-ACCESS  read-only
     STATUS      current
     DESCRIPTION
             "This object shows the CCM DB vlan."
     ::= { wwpLeosCfmMipCCMDbEntry 1 }
      
 wwpLeosCfmMipCCMDbVid OBJECT-TYPE
     SYNTAX      Unsigned32 (1..24576)
     MAX-ACCESS  read-only
     STATUS      current
     DESCRIPTION
             "This object shows the CCM DB vlan."
     ::= { wwpLeosCfmMipCCMDbEntry 2 }
 
 wwpLeosCfmMipCCMDbMacAddr OBJECT-TYPE
     SYNTAX      MacAddress
     MAX-ACCESS  read-only
     STATUS      current
     DESCRIPTION
             "This object shows the mac address."
     ::= { wwpLeosCfmMipCCMDbEntry 3 }
 
 wwpLeosCfmMipCCMDbPort OBJECT-TYPE
     SYNTAX      INTEGER (1..65535)
     MAX-ACCESS  read-only
     STATUS      current
     DESCRIPTION
             "This object shows the CCM DB port."
     ::= { wwpLeosCfmMipCCMDbEntry 4 }         
     
 wwpLeosCfmMipCCMDbMEPID OBJECT-TYPE
     SYNTAX      INTEGER (1..8191)
     MAX-ACCESS  read-only
     STATUS      current
     DESCRIPTION
             "This object shows the CCM DB MEP ID."
     ::= { wwpLeosCfmMipCCMDbEntry 5 }        
     
 wwpLeosCfmMipCCMdbNumCCMRx OBJECT-TYPE
     SYNTAX      Counter32
     MAX-ACCESS  read-only
     STATUS      current
     DESCRIPTION
             "This object shows the number of CCM DB packets received."
     ::= { wwpLeosCfmMipCCMDbEntry 6 } 
     
 wwpLeosCfmMipCCMDbTime OBJECT-TYPE
     SYNTAX      TimeTicks
     MAX-ACCESS  read-only
     STATUS      current
     DESCRIPTION
             "This object shows the CCM DB time."
     ::= { wwpLeosCfmMipCCMDbEntry 7 } 
     
 wwpLeosCfmMipCCMDbLastMacStatus OBJECT-TYPE
     SYNTAX      TruthValue
     MAX-ACCESS  read-only
     STATUS      current
     DESCRIPTION
             "This object shows the CCM DB last mac status."
     ::= { wwpLeosCfmMipCCMDbEntry 8 }
     
  wwpLeosCfmMipCCMDbRDIErrorFlag OBJECT-TYPE
     SYNTAX      TruthValue
     MAX-ACCESS  read-only
     STATUS      current
     DESCRIPTION
             "This object shows the CCM DB RDI error flag status."
     ::= { wwpLeosCfmMipCCMDbEntry 9 }
  
 --
 -- CFM Faults
 --  
 wwpLeosCfmServiceFaultTable OBJECT-TYPE
     SYNTAX     SEQUENCE OF WwpLeosCfmServiceFaultEntry
     MAX-ACCESS not-accessible
     STATUS     current
     DESCRIPTION
            "The (conceptual) table used for Fault Traps.
             The last CFM error that occurred is reported."  
     ::= { wwpLeosCfmService 2 }
                
 wwpLeosCfmServiceFaultEntry OBJECT-TYPE
     SYNTAX      WwpLeosCfmServiceFaultEntry
     MAX-ACCESS  not-accessible
     STATUS      current
     DESCRIPTION
           "An entry (conceptual row) in the wwpLeosCfmServiceFaultTable."
     INDEX { wwpLeosCfmServiceIndex }
     ::= { wwpLeosCfmServiceFaultTable 1 }
                
 WwpLeosCfmServiceFaultEntry ::=  SEQUENCE {                      
 	wwpLeosCfmServiceFaultTime    	TimeTicks,
 	wwpLeosCfmServiceFaultType		INTEGER,
 	wwpLeosCfmServiceFaultDesc		DisplayString,
 	wwpLeosCfmServiceFaultMep		INTEGER,
 	wwpLeosCfmServiceVlan			INTEGER,
    wwpLeosCfmServiceVsPbtName      DisplayString
 }
   
 wwpLeosCfmServiceFaultTime OBJECT-TYPE
     SYNTAX      TimeTicks 
     MAX-ACCESS  read-only
     STATUS      current
     DESCRIPTION
             "This object specifies the time at which the fault occurred."
     ::= { wwpLeosCfmServiceFaultEntry 1 }
 
 wwpLeosCfmServiceFaultType OBJECT-TYPE
     SYNTAX      INTEGER  {         
     				none(1),
     				someRDIDefect(2),
     				someMACStatusDefect(3),
     				someRMEPCCMDefect(4),
     				errorCCMDefect(5),
     				xconCCMDefect(6),
     				instability(7)
     				}
     MAX-ACCESS  read-only
     STATUS      current
     DESCRIPTION
             "This object specifies the type of fault."
     ::= { wwpLeosCfmServiceFaultEntry 2 }

wwpLeosCfmServiceFaultDesc OBJECT-TYPE
     SYNTAX      DisplayString
     MAX-ACCESS  read-only
     STATUS      current
     DESCRIPTION
             "This object specifies the description of the fault."
     ::= { wwpLeosCfmServiceFaultEntry 3 }
 
wwpLeosCfmServiceFaultMep OBJECT-TYPE
     SYNTAX      INTEGER (1..8191)
     MAX-ACCESS  read-only
     STATUS      current
     DESCRIPTION
             "This object specifies the Mepid of MEP reporting the fault."
     ::= { wwpLeosCfmServiceFaultEntry 4 }
     
 wwpLeosCfmServiceVlan OBJECT-TYPE
     SYNTAX      INTEGER (1..65535)
     MAX-ACCESS  read-only
     STATUS      current
     DESCRIPTION
             "This object specifies the service VLAN."
     ::= { wwpLeosCfmServiceFaultEntry 5 } 

  wwpLeosCfmServiceVsPbtName OBJECT-TYPE
     SYNTAX      DisplayString (SIZE(0..31))
     MAX-ACCESS  read-only
     STATUS      current
     DESCRIPTION
             "This object represents the virtual switch or Pbt tunnel assigned to the given service." 
     ::= { wwpLeosCfmServiceFaultEntry 50 }
  
 --
 -- CFM SERVICE STATISTICS TABLE
 --
 wwpLeosCfmServiceStatisticsTable OBJECT-TYPE
     SYNTAX     SEQUENCE OF WwpLeosCfmServiceStatisticsEntry
     MAX-ACCESS not-accessible
     STATUS     current
     DESCRIPTION
            "The (conceptual) table listing the configuration
            parameters for the CFM Service Table.
            
            To create an entry in this table, the following criteria must be met:
            wwpLeosCfmServiceType must be specified.
            wwpLeosCfmServiceValue must be specified.
            wwpLeosCfmServiceName must be specified.
            wwpLeosCfmServiceStatus must be set to createAndGo."  
     ::= { wwpLeosCfmService 3 }

 
 wwpLeosCfmServiceStatisticsEntry OBJECT-TYPE
     SYNTAX      WwpLeosCfmServiceStatisticsEntry
     MAX-ACCESS  not-accessible
     STATUS      current
     DESCRIPTION
           "An entry (conceptual row) in the wwpLeosCfmServiceTable."
     INDEX {wwpLeosCfmServiceIndex}
     ::= { wwpLeosCfmServiceStatisticsTable 1 }
 
 WwpLeosCfmServiceStatisticsEntry ::=  SEQUENCE {  
 	          wwpLeosCfmServiceRxTotalValidFrames 				Counter64,
 	          wwpLeosCfmServiceRxTotalInvalidFrames 			Counter64,
 	          wwpLeosCfmServiceInvalidMessageOverflow 			Counter64,
 	          wwpLeosCfmServiceInvalidPortStatusTLV  			Counter64,
 	          wwpLeosCfmServiceInvalidInterfaceStatusTLV 		Counter64,
 	          wwpLeosCfmServiceInvalidSenderIDTLV 				Counter64,
 	          wwpLeosCfmServiceTxTotalCCM 						Counter64,
 	          wwpLeosCfmServiceTotalRxValidCCM 					Counter64,
 	          wwpLeosCfmServiceTotalRxInSequenceCCM 			Counter64,
 	          wwpLeosCfmServiceTotalRxNotInSequenceCCM 			Counter64,
 	          wwpLeosCfmServiceTotalRxMDLevelXconCCM 			Counter64,
 	          wwpLeosCfmServiceTotalRxMAIDXconCCM    			Counter64, 
 	          wwpLeosCfmServiceTotalRxMEPIDErrorCCM  			Counter64,
 	          wwpLeosCfmServiceTotalRxCCMIntervalErrorCCM 		Counter64,
 	          wwpLeosCfmServiceTotalRxInvalidCCM     			Counter64,
 	          wwpLeosCfmServiceTotalTxLTM						Counter64,
 	          wwpLeosCfmServiceTotalTxLTR						Counter64,
 	          wwpLeosCfmServiceTotalRxValidLTR					Counter64,
 	          wwpLeosCfmServiceTotalRxUnexpectedLTR				Counter64,
 	          wwpLeosCfmServiceTotalRxInvalidLTR				Counter64,
 	          wwpLeosCfmServiceTotalRxInvalidRelayActionLTR     Counter64,
 	          wwpLeosCfmServiceTotalRxValidLTM					Counter64,
 	          wwpLeosCfmServiceTotalTxInvalidLTM				Counter64,
 	          wwpLeosCfmServiceTotalTxLBM						Counter64,
 	          wwpLeosCfmServiceTotalTxLBR						Counter64,
 	          wwpLeosCfmServiceTotalRxInorderLBR				Counter64,
 	          wwpLeosCfmServiceTotalRxOutOfOrderLBR				Counter64,
 	          wwpLeosCfmServiceTotalRxContentMismatchLBR		Counter64,
 	          wwpLeosCfmServiceTotalRxUnexpectedLBR				Counter64,
 	          wwpLeosCfmServiceTotalRxInvalidLBR 				Counter64,
 	          wwpLeosCfmServiceTotalRxValidLBM					Counter64,
 	          wwpLeosCfmServiceTotalRxInvalidLBM				Counter64,
 	          wwpLeosCfmServiceTotalTxDMM						Counter64, 
 	          wwpLeosCfmServiceTotalTxDMR						Counter64,
 	          wwpLeosCfmServiceTotalRxDMM						Counter64,
 	          wwpLeosCfmServiceTotalRxDMR						Counter64, 
 	          wwpLeosCfmServiceTotalTxLMM						Counter64,
 	          wwpLeosCfmServiceTotalTxLMR						Counter64,
 	          wwpLeosCfmServiceTotalRxLMM						Counter64,
 	          wwpLeosCfmServiceTotalRxLMR						Counter64,
 	          wwpLeosCfmServiceStatsClear						INTEGER,
 	          wwpLeosCfmServiceTotalTxSLM						Counter64,
 	          wwpLeosCfmServiceTotalTxSLR						Counter64,
 	          wwpLeosCfmServiceTotalRxSLM						Counter64,
 	          wwpLeosCfmServiceTotalRxSLR						Counter64,
 	          wwpLeosCfmServiceTotalTxCSF						Counter64,
 	          wwpLeosCfmServiceTotalTxCSFLos					Counter64,
 	          wwpLeosCfmServiceTotalTxCSFDci					Counter64,
 	          wwpLeosCfmServiceTotalRxCSF						Counter64,
 	          wwpLeosCfmServiceTotalRxCSFLos					Counter64,
 	          wwpLeosCfmServiceTotalRxCSFDci					Counter64,
 	          wwpLeosCfmServiceTotalRxInvalidCSF				Counter64
 }
 
 wwpLeosCfmServiceRxTotalValidFrames	OBJECT-TYPE
 	SYNTAX  Counter64 
 	MAX-ACCESS read-only
 	STATUS current
 	DESCRIPTION
 		"The total valid Frames received."
 	::= { wwpLeosCfmServiceStatisticsEntry 1 }
 
 wwpLeosCfmServiceRxTotalInvalidFrames	OBJECT-TYPE
 	SYNTAX Counter64
 	MAX-ACCESS read-only
 	STATUS current
 	DESCRIPTION
 		"The total invalid Frames received."
 	::= { wwpLeosCfmServiceStatisticsEntry 2 }
 
 wwpLeosCfmServiceInvalidMessageOverflow	OBJECT-TYPE
 	SYNTAX Counter64
 	MAX-ACCESS read-only
 	STATUS current
 	DESCRIPTION
 		"The total invalid message overflow Frames."
 	::= { wwpLeosCfmServiceStatisticsEntry 3 }
 
  wwpLeosCfmServiceInvalidPortStatusTLV		OBJECT-TYPE
  	SYNTAX Counter64
  	MAX-ACCESS read-only
 	STATUS current
 	DESCRIPTION
 		"The total invalid Port Status TLVs Frames."
 	::= { wwpLeosCfmServiceStatisticsEntry 4 }
    
  wwpLeosCfmServiceInvalidInterfaceStatusTLV   OBJECT-TYPE
  	SYNTAX Counter64
  	MAX-ACCESS read-only
 	STATUS current
 	DESCRIPTION
 		"The invalid interface Status TLVs Frames."
 	::= { wwpLeosCfmServiceStatisticsEntry 5 }
 
   wwpLeosCfmServiceInvalidSenderIDTLV	OBJECT-TYPE
   	SYNTAX Counter64
  	MAX-ACCESS read-only
 	STATUS current
 	DESCRIPTION
 		"The invalid SenderId TLV."
 	::= { wwpLeosCfmServiceStatisticsEntry 6 }
    
    wwpLeosCfmServiceTxTotalCCM		OBJECT-TYPE
    SYNTAX Counter64
    MAX-ACCESS read-only
 	STATUS current
 	DESCRIPTION
 		"The total CCM sent."
 	::= { wwpLeosCfmServiceStatisticsEntry 7 }        
 	
 	wwpLeosCfmServiceTotalRxValidCCM  OBJECT-TYPE
    SYNTAX Counter64
    MAX-ACCESS read-only
 	STATUS current
 	DESCRIPTION
 		"The total valid CCM received."
 	::= { wwpLeosCfmServiceStatisticsEntry 8 } 
 	
 	wwpLeosCfmServiceTotalRxInSequenceCCM	OBJECT-TYPE
 	SYNTAX Counter64
 	MAX-ACCESS read-only
 	STATUS current
 	DESCRIPTION
 		"The total CCM in sequence received."
 	::= { wwpLeosCfmServiceStatisticsEntry 9 }                         
 	
 	wwpLeosCfmServiceTotalRxNotInSequenceCCM  	OBJECT-TYPE
 		SYNTAX Counter64
 		 MAX-ACCESS read-only
 		STATUS current
 		DESCRIPTION
 		"The total CCM not in sequence received."
 	::= { wwpLeosCfmServiceStatisticsEntry 10 } 
 	
 	wwpLeosCfmServiceTotalRxMDLevelXconCCM		OBJECT-TYPE
 		SYNTAX Counter64
 		MAX-ACCESS read-only
 		STATUS current
 		DESCRIPTION
 		"The total MD Level Xcon CCM received."
 	::= { wwpLeosCfmServiceStatisticsEntry 11 } 		    
 	
 	wwpLeosCfmServiceTotalRxMAIDXconCCM		OBJECT-TYPE
 		SYNTAX Counter64
 		MAX-ACCESS read-only
 		STATUS current
 		DESCRIPTION
 		"The total MAID Xcon CCM received."
 	::= { wwpLeosCfmServiceStatisticsEntry 12 }    
 	
 	wwpLeosCfmServiceTotalRxMEPIDErrorCCM    OBJECT-TYPE
 		SYNTAX Counter64
 		MAX-ACCESS read-only
 		STATUS current
 		DESCRIPTION
 		"The total MEPID Error CCM received."
 	::= { wwpLeosCfmServiceStatisticsEntry 13 }            
 	
 	wwpLeosCfmServiceTotalRxCCMIntervalErrorCCM		OBJECT-TYPE
 		SYNTAX Counter64
 		MAX-ACCESS read-only
 		STATUS current
 		DESCRIPTION
 		"The total Interval Error CCM received."
 	::= { wwpLeosCfmServiceStatisticsEntry 14 }        
 	
 	wwpLeosCfmServiceTotalRxInvalidCCM		OBJECT-TYPE
 		SYNTAX Counter64
 		MAX-ACCESS read-only
 		STATUS current
 		DESCRIPTION
 		"The total Internal Error CCM received."
 	::= { wwpLeosCfmServiceStatisticsEntry 15 }  
 	
 	wwpLeosCfmServiceTotalTxLTM		OBJECT-TYPE
 		SYNTAX Counter64
 		MAX-ACCESS read-only
 		STATUS current
 		DESCRIPTION
 		"The total Internal Error CCM received."
 	::= { wwpLeosCfmServiceStatisticsEntry 16 }
 	
 	wwpLeosCfmServiceTotalTxLTR	 OBJECT-TYPE
 		SYNTAX Counter64
 		MAX-ACCESS read-only
 		STATUS current
 		DESCRIPTION
 		"The total Internal Error CCM received."
 	::= { wwpLeosCfmServiceStatisticsEntry 17 }
 	
 	wwpLeosCfmServiceTotalRxValidLTR OBJECT-TYPE
 		SYNTAX Counter64
 		MAX-ACCESS read-only
 		STATUS current
 		DESCRIPTION
 		"The valid LTR Received."
 	::= { wwpLeosCfmServiceStatisticsEntry 18 } 
 	
 	wwpLeosCfmServiceTotalRxUnexpectedLTR OBJECT-TYPE
 		SYNTAX Counter64
 		MAX-ACCESS read-only
 		STATUS current
 		DESCRIPTION
 		"The unexpected LTR received. "
 	::= { wwpLeosCfmServiceStatisticsEntry 19 }
 	
 	wwpLeosCfmServiceTotalRxInvalidLTR	OBJECT-TYPE
 		SYNTAX Counter64
 		MAX-ACCESS read-only
 		STATUS current
 		DESCRIPTION
 		"This object specifies invalid LTR received. "
 	::= { wwpLeosCfmServiceStatisticsEntry 20 }
 	
 	wwpLeosCfmServiceTotalRxInvalidRelayActionLTR OBJECT-TYPE
 		SYNTAX Counter64
 		MAX-ACCESS read-only
 		STATUS current
 		DESCRIPTION
 		"The total invalid relay action LTR received."
 	::= { wwpLeosCfmServiceStatisticsEntry 21 }
 	
 	wwpLeosCfmServiceTotalRxValidLTM  OBJECT-TYPE
 		SYNTAX Counter64
 		MAX-ACCESS read-only
 		STATUS current
 		DESCRIPTION
 		"The valid LTM received."
 	::= { wwpLeosCfmServiceStatisticsEntry 22 } 
 	
 	wwpLeosCfmServiceTotalTxInvalidLTM  OBJECT-TYPE
 		SYNTAX Counter64
 		MAX-ACCESS read-only
 		STATUS current
 		DESCRIPTION
 		"The total invalid LTM sent."
 	::= { wwpLeosCfmServiceStatisticsEntry 23 } 
 	
 	wwpLeosCfmServiceTotalTxLBM	 OBJECT-TYPE
 		SYNTAX Counter64
 		MAX-ACCESS read-only
 		STATUS current
 		DESCRIPTION
 		"The total LBM sent."
 	::= { wwpLeosCfmServiceStatisticsEntry 24 } 
 	
 	wwpLeosCfmServiceTotalTxLBR OBJECT-TYPE
 		SYNTAX Counter64
 		MAX-ACCESS read-only
 		STATUS current
 		DESCRIPTION
 		"The total LBR sent."
 	::= { wwpLeosCfmServiceStatisticsEntry 25 } 
 	
 	wwpLeosCfmServiceTotalRxInorderLBR OBJECT-TYPE
 		SYNTAX Counter64
 		MAX-ACCESS read-only
 		STATUS current
 		DESCRIPTION
 		"The total in order LBR received."
 	::= { wwpLeosCfmServiceStatisticsEntry 26 } 
 	
 	wwpLeosCfmServiceTotalRxOutOfOrderLBR  OBJECT-TYPE
 		SYNTAX Counter64
 		MAX-ACCESS read-only
 		STATUS current
 		DESCRIPTION
 		"The toal out of order LBR received."
 	::= { wwpLeosCfmServiceStatisticsEntry 27 }  
 	
 	wwpLeosCfmServiceTotalRxContentMismatchLBR OBJECT-TYPE
 		SYNTAX Counter64
 		MAX-ACCESS read-only
 		STATUS current
 		DESCRIPTION
 		"The total content mismatch LBR received."
 	::= { wwpLeosCfmServiceStatisticsEntry 28 }  
 	
 	wwpLeosCfmServiceTotalRxUnexpectedLBR  OBJECT-TYPE
 		SYNTAX Counter64
 		MAX-ACCESS read-only
 		STATUS current
 		DESCRIPTION
 		"The total unexpected LBR received."
 	::= { wwpLeosCfmServiceStatisticsEntry 29 } 
 	
 	wwpLeosCfmServiceTotalRxInvalidLBR	OBJECT-TYPE
 		SYNTAX Counter64
 		MAX-ACCESS read-only
 		STATUS current
 		DESCRIPTION
 		"The invalid LBR received."
 	::= { wwpLeosCfmServiceStatisticsEntry 30 } 
 	
 	wwpLeosCfmServiceTotalRxValidLBM OBJECT-TYPE
 		SYNTAX Counter64
 		MAX-ACCESS read-only
 		STATUS current
 		DESCRIPTION
 		"The valid LBM received."
 	::= { wwpLeosCfmServiceStatisticsEntry 31 }   
 	
 	wwpLeosCfmServiceTotalRxInvalidLBM	OBJECT-TYPE
 		SYNTAX Counter64
 		MAX-ACCESS read-only
 		STATUS current
 		DESCRIPTION
 		"The total invalid LBM received."
 	::= { wwpLeosCfmServiceStatisticsEntry 32 }    
 	

 	wwpLeosCfmServiceTotalTxDMM		OBJECT-TYPE
 		SYNTAX Counter64
 		MAX-ACCESS read-only
 		STATUS current
 		DESCRIPTION
 		 "The total DMM sent. "
 	::= { wwpLeosCfmServiceStatisticsEntry 33 }
 	
 	wwpLeosCfmServiceTotalTxDMR	OBJECT-TYPE
 		SYNTAX Counter64
 		MAX-ACCESS read-only
 		STATUS current
 		DESCRIPTION
 		"The total DMR sent."
 	::= { wwpLeosCfmServiceStatisticsEntry 34 }
 	
 	wwpLeosCfmServiceTotalRxDMM		OBJECT-TYPE
 		SYNTAX   Counter64
 		MAX-ACCESS read-only
 		STATUS current
 		DESCRIPTION
 		"The total DMM received."
 	::= { wwpLeosCfmServiceStatisticsEntry 35 } 
 	
 	wwpLeosCfmServiceTotalRxDMR		OBJECT-TYPE
 		SYNTAX   Counter64
 		MAX-ACCESS read-only
 		STATUS current
 		DESCRIPTION
 		"The total DMR received."
 	::= { wwpLeosCfmServiceStatisticsEntry 36 } 
	
	wwpLeosCfmServiceTotalTxLMM		OBJECT-TYPE
 		SYNTAX   Counter64
 		MAX-ACCESS read-only
 		STATUS current
 		DESCRIPTION
 		"The total LMM sent."
 	::= { wwpLeosCfmServiceStatisticsEntry 37 } 
 	
 	wwpLeosCfmServiceTotalTxLMR  OBJECT-TYPE
 		SYNTAX   Counter64
 		MAX-ACCESS read-only
 		STATUS current
 		DESCRIPTION
 		"The total LMR sent."
 	::= { wwpLeosCfmServiceStatisticsEntry 38 } 
	
	wwpLeosCfmServiceTotalRxLMM	OBJECT-TYPE
 		SYNTAX   Counter64
 		MAX-ACCESS read-only
 		STATUS current
 		DESCRIPTION
 		"The total LMM received."
 	::= { wwpLeosCfmServiceStatisticsEntry 39 } 
 	
 	wwpLeosCfmServiceTotalRxLMR  OBJECT-TYPE
 		SYNTAX   Counter64
 		MAX-ACCESS read-only
 		STATUS current
 		DESCRIPTION
 		"The total LMR received. "
 	::= { wwpLeosCfmServiceStatisticsEntry 40 }
  
   wwpLeosCfmServiceStatsClear OBJECT-TYPE
   	  SYNTAX INTEGER 
   	  		{
   	  			clear(1),
   	  			none(2)
   	  		}
   	  MAX-ACCESS read-write
   	  STATUS current
   	  DESCRIPTION 
   	  "Setting this object to clear(1) clears statistics for the given service index.
   	   This object cannot be set to none"
   	  ::=   { wwpLeosCfmServiceStatisticsEntry 41 }  
   	  
   wwpLeosCfmServiceTotalTxSLM		OBJECT-TYPE
 		SYNTAX   Counter64
 		MAX-ACCESS read-only
 		STATUS current
 		DESCRIPTION
 		"The total LMM sent."
 	::= { wwpLeosCfmServiceStatisticsEntry 42 } 
 	
 	wwpLeosCfmServiceTotalTxSLR  OBJECT-TYPE
 		SYNTAX   Counter64
 		MAX-ACCESS read-only
 		STATUS current
 		DESCRIPTION
 		"The total LMR sent."
 	::= { wwpLeosCfmServiceStatisticsEntry 43 } 
	
	wwpLeosCfmServiceTotalRxSLM	OBJECT-TYPE
 		SYNTAX   Counter64
 		MAX-ACCESS read-only
 		STATUS current
 		DESCRIPTION
 		"The total LMM received."
 	::= { wwpLeosCfmServiceStatisticsEntry 44 } 
 	
 	wwpLeosCfmServiceTotalRxSLR  OBJECT-TYPE
 		SYNTAX   Counter64
 		MAX-ACCESS read-only
 		STATUS current
 		DESCRIPTION
 		"The total LMR received. "
 	::= { wwpLeosCfmServiceStatisticsEntry 45 }
	  
 	wwpLeosCfmServiceTotalTxCSF  OBJECT-TYPE
 		SYNTAX   Counter64
 		MAX-ACCESS read-only
 		STATUS current
 		DESCRIPTION
 		"The total CSF transmitted."
 	::= { wwpLeosCfmServiceStatisticsEntry 46 }

 	wwpLeosCfmServiceTotalTxCSFLos  OBJECT-TYPE
 		SYNTAX   Counter64
 		MAX-ACCESS read-only
 		STATUS current
 		DESCRIPTION
 		"The total CSF Los frames transmitted."
 	::= { wwpLeosCfmServiceStatisticsEntry 47 }

 	wwpLeosCfmServiceTotalTxCSFDci  OBJECT-TYPE
 		SYNTAX   Counter64
 		MAX-ACCESS read-only
 		STATUS current
 		DESCRIPTION
 		"The total CSF Dci frames transmitted."
 	::= { wwpLeosCfmServiceStatisticsEntry 48 }

 	wwpLeosCfmServiceTotalRxCSF  OBJECT-TYPE
 		SYNTAX   Counter64
 		MAX-ACCESS read-only
 		STATUS current
 		DESCRIPTION
 		"The total CSF received."
 	::= { wwpLeosCfmServiceStatisticsEntry 49 }

 	wwpLeosCfmServiceTotalRxCSFLos  OBJECT-TYPE
 		SYNTAX   Counter64
 		MAX-ACCESS read-only
 		STATUS current
 		DESCRIPTION
 		"The total CSF Los frames received."
 	::= { wwpLeosCfmServiceStatisticsEntry 50 }

 	wwpLeosCfmServiceTotalRxCSFDci  OBJECT-TYPE
 		SYNTAX   Counter64
 		MAX-ACCESS read-only
 		STATUS current
 		DESCRIPTION
 		"The total CSF Dci frames received."
 	::= { wwpLeosCfmServiceStatisticsEntry 51 }

 	wwpLeosCfmServiceTotalRxInvalidCSF  OBJECT-TYPE
 		SYNTAX   Counter64
 		MAX-ACCESS read-only
 		STATUS current
 		DESCRIPTION
 		"The total invalid CSF frames received."
 	::= { wwpLeosCfmServiceStatisticsEntry 52 }


   wwpLeosCfmServiceClearStats OBJECT-TYPE
 	SYNTAX INTEGER {
 		clear(1),
 		none(2)
 		}
 	MAX-ACCESS read-write
 	STATUS current
 	DESCRIPTION "Setting this object to clear(1) clears all service level statistics for all services and within each mep."
 	DEFVAL {none}
 	::= {wwpLeosCfmService 4}
                                                      
  --
  -- Delay Measurement Msg table
  -- 
  wwpLeosCfmDelayMsgTable OBJECT-TYPE
     SYNTAX     SEQUENCE OF WwpLeosCfmDelayMsgEntry
     MAX-ACCESS not-accessible
     STATUS     obsolete
     DESCRIPTION
            "The (conceptual) table listing the configuration 
            parameters for the DelayMeasurementMsg.
            This table is marked as obsolete as the functionality
            shifted to wwpLeosCfmExtDelayMsgTable."  
     ::= { wwpLeosCfmDelay 1 }
                
 wwpLeosCfmDelayMsgEntry OBJECT-TYPE
     SYNTAX      WwpLeosCfmDelayMsgEntry
     MAX-ACCESS  not-accessible
     STATUS      obsolete
     DESCRIPTION
           "An entry (conceptual row) in the wwpLeosCfmDelayMsgTable."
     INDEX {wwpLeosCfmServiceIndex, wwpLeosCfmDelayMsgPortId}
     ::= { wwpLeosCfmDelayMsgTable 1 }
                
 WwpLeosCfmDelayMsgEntry ::=  SEQUENCE { 
     wwpLeosCfmDelayMsgPortId                  	INTEGER,
     wwpLeosCfmDelayMsgTargetMEPID              Unsigned32,
     wwpLeosCfmDelayMsgTargetMacAddr            MacAddress,
     wwpLeosCfmDelayMsgCount                   	INTEGER,
     wwpLeosCfmDelayMsgPriority                	INTEGER,
     wwpLeosCfmDelayMsgRowStatus               	RowStatus,
     wwpLeosCfmDelayMsgRepeat					INTEGER,
     wwpLeosCfmDelayMsgRepeatCount				INTEGER,
     wwpLeosCfmDelayMsgDelayThreshold			INTEGER,
     wwpLeosCfmDelayMsgJitterThreshold			INTEGER,
     wwpLeosCfmDelayMsgMaxDelayThreshold		INTEGER,
     wwpLeosCfmDelayMsgMaxJitterThreshold		INTEGER

 }

 wwpLeosCfmDelayMsgPortId OBJECT-TYPE
     SYNTAX       INTEGER (1..65535)
     MAX-ACCESS   read-only
     STATUS       obsolete
     DESCRIPTION
             "This object specifies the port."
     ::= { wwpLeosCfmDelayMsgEntry 1 }
 
 wwpLeosCfmDelayMsgTargetMEPID OBJECT-TYPE
     SYNTAX       Unsigned32 (1..8191)
     MAX-ACCESS   read-create
     STATUS       obsolete
     DESCRIPTION
             "This object specifies the MEPID.
              This object should only be set if wwpLeosCfmDelayMsgTargetMacAddr is not specified else 
              an error is returned."
     ::= { wwpLeosCfmDelayMsgEntry 2 }
     
 wwpLeosCfmDelayMsgTargetMacAddr OBJECT-TYPE
     SYNTAX       MacAddress
     MAX-ACCESS   read-create
     STATUS       obsolete
     DESCRIPTION
             "This object specifies the MacAddress to be used when sending link LoopbackMsg.
              This object should only be set if wwpLeosCfmDelayMsgTargetMEPID is not specified else 
              an error is returned."
     ::= { wwpLeosCfmDelayMsgEntry 3 }
     
 wwpLeosCfmDelayMsgCount OBJECT-TYPE
     SYNTAX       INTEGER (2..600) 
     MAX-ACCESS   read-create
     STATUS       obsolete
     DESCRIPTION
             "This object specifies the DelayMeasurementMsg count to be used
              when sending link DelayMeasurementMsg."
     ::= { wwpLeosCfmDelayMsgEntry 4 }
 
 wwpLeosCfmDelayMsgPriority OBJECT-TYPE
     SYNTAX       INTEGER (0..7)
     MAX-ACCESS   read-create
     STATUS       obsolete
     DESCRIPTION
             "This object specifies the DelayMeasurementMsg priority to be
             used when sending link DelayMeasurementMsg."
     ::= { wwpLeosCfmDelayMsgEntry 5 }
 
 wwpLeosCfmDelayMsgRowStatus OBJECT-TYPE
     SYNTAX       RowStatus
     MAX-ACCESS   read-create
     STATUS       obsolete
     DESCRIPTION
             "Used to manage the creation and deletion of the conceptual rows in this table.
	     To create a row in this table, set this object to 'createAndGo'. 
	     To delete a row in this table, set this to 'destroy'.
             If 'destroy' is used and either TargetMacAddr or TargetMEPID is
             specified, a cancel is done for any repeating test on those items."
     ::= { wwpLeosCfmDelayMsgEntry 6 }  
     
 wwpLeosCfmDelayMsgRepeat OBJECT-TYPE
 	 SYNTAX			INTEGER {
 	 					enable(1),
 	 					disable(2)
 	 					}
 	 MAX-ACCESS		read-create
 	 STATUS			obsolete
 	 DESCRIPTION
 	 		"Used to make the Delay Measurement test a repeating test."
 	 ::= { wwpLeosCfmDelayMsgEntry 7 } 
 	 
 wwpLeosCfmDelayMsgRepeatCount OBJECT-TYPE
 	SYNTAX			INTEGER (0..1440)
 	MAX-ACCESS		read-create
 	STATUS			obsolete
 	DESCRIPTION
 			"The repeat time in minutes for the Delay Measurement test.
 			If zero is specified, the test runs continuously."
 	::= { wwpLeosCfmDelayMsgEntry 8 }  
 	
 wwpLeosCfmDelayMsgDelayThreshold OBJECT-TYPE
 	SYNTAX			INTEGER (-1..2147483647)
 	MAX-ACCESS		read-create
 	STATUS			obsolete
 	DESCRIPTION
 			"The fault threshold for the Delay Measurement test, specified
 			in microseconds.  A value of -1 disables the generate of faults.
 			A value of 0 or greater is compared to the average delay result of the
 			test and a fault is generated if the threshold is exceeded."
 	::= { wwpLeosCfmDelayMsgEntry 9 }
 
 wwpLeosCfmDelayMsgJitterThreshold OBJECT-TYPE
 	SYNTAX			INTEGER (-1..2147483647)
 	MAX-ACCESS		read-create
 	STATUS			obsolete
 	DESCRIPTION
 			"The fault threshold for the Jitter Measurement test, specified
 			in microseconds.  A value of -1 disables the generate of faults.
 			A value of 0 or greater is compared to the average jitter result of the
 			test and a fault is generated if the threshold is exceeded."
 	::= { wwpLeosCfmDelayMsgEntry 10 }
 	
 wwpLeosCfmDelayMsgMaxDelayThreshold OBJECT-TYPE
 	SYNTAX			INTEGER (-1..2147483647)
 	MAX-ACCESS		read-create
 	STATUS			obsolete
 	DESCRIPTION
 			"The fault threshold for the Delay Measurement test, specified
 			in microseconds.  A value of -1 disables the generate of faults.
 			A value of 0 or greater is compared to the maximum delay result of the
 			test and a fault is generated if the threshold is exceeded."
 	::= { wwpLeosCfmDelayMsgEntry 11 }
 
 wwpLeosCfmDelayMsgMaxJitterThreshold OBJECT-TYPE
 	SYNTAX			INTEGER (-1..2147483647)
 	MAX-ACCESS		read-create
 	STATUS			obsolete
 	DESCRIPTION
 			"The fault threshold for the Jitter Measurement test, specified
 			in microseconds.  A value of -1 disables the generate of faults.
 			A value of 0 or greater is compared to the maximum jitter result of the
 			test and a fault is generated if the threshold is exceeded."
 	::= { wwpLeosCfmDelayMsgEntry 12 }

  --
  -- Frame Loss Measurement Msg table
  -- 
  wwpLeosCfmFrameLossMsgTable OBJECT-TYPE
     SYNTAX     SEQUENCE OF WwpLeosCfmFrameLossMsgEntry
     MAX-ACCESS not-accessible
     STATUS     obsolete
     DESCRIPTION
            "The (conceptual) table listing the configuration 
            parameters for the FrameLossMeasurementMsg.
            This table is marked as obsolete as the functionality
            shifted to wwpLeosCfmExtFrameLossMsgTable."  
     ::= { wwpLeosCfmFrameLoss 1 }
                
 wwpLeosCfmFrameLossMsgEntry OBJECT-TYPE
     SYNTAX      WwpLeosCfmFrameLossMsgEntry
     MAX-ACCESS  not-accessible
     STATUS      obsolete
     DESCRIPTION
           "An entry (conceptual row) in the wwpLeosCfmFrameLossMsgTable."
     INDEX {wwpLeosCfmServiceIndex, wwpLeosCfmFrameLossMsgPortId}
     ::= { wwpLeosCfmFrameLossMsgTable 1 }
                
 WwpLeosCfmFrameLossMsgEntry ::=  SEQUENCE { 
     wwpLeosCfmFrameLossMsgPortId                  	INTEGER,
     wwpLeosCfmFrameLossMsgTargetMEPID              Unsigned32,
     wwpLeosCfmFrameLossMsgTargetMacAddr            MacAddress,
     wwpLeosCfmFrameLossMsgCount                   	INTEGER,
     wwpLeosCfmFrameLossMsgPriority                	INTEGER,
     wwpLeosCfmFrameLossMsgRowStatus               	RowStatus,
     wwpLeosCfmFrameLossMsgRepeat					INTEGER,
     wwpLeosCfmFrameLossMsgRepeatCount				INTEGER,
     wwpLeosCfmFrameLossMsgFlnThreshold				INTEGER,
     wwpLeosCfmFrameLossMsgFlfThreshold				INTEGER
 }

 wwpLeosCfmFrameLossMsgPortId OBJECT-TYPE
     SYNTAX       INTEGER (1..65535)
     MAX-ACCESS   read-only
     STATUS       obsolete
     DESCRIPTION
             "This object specifies the port."
     ::= { wwpLeosCfmFrameLossMsgEntry 1 }
 
 wwpLeosCfmFrameLossMsgTargetMEPID OBJECT-TYPE
     SYNTAX       Unsigned32 (1..8191)
     MAX-ACCESS   read-create
     STATUS       obsolete
     DESCRIPTION
             "This object specifies the MEPID.
              This object should only be set if wwpLeosCfmFrameLossMsgTargetMacAddr is not specified else 
              an error is returned."
     ::= { wwpLeosCfmFrameLossMsgEntry 2 }
     
 wwpLeosCfmFrameLossMsgTargetMacAddr OBJECT-TYPE
     SYNTAX       MacAddress
     MAX-ACCESS   read-create
     STATUS       obsolete
     DESCRIPTION
             "This object specifies the MacAddress to be used when sending link LoopbackMsg.
              This object should only be set if wwpLeosCfmFrameLossMsgTargetMEPID is not specified else 
              an error is returned."
     ::= { wwpLeosCfmFrameLossMsgEntry 3 }
     
 wwpLeosCfmFrameLossMsgCount OBJECT-TYPE
     SYNTAX       INTEGER (2..600) 
     MAX-ACCESS   read-create
     STATUS       obsolete
     DESCRIPTION
             "This object specifies the FrameLossMeasurementMsg count to be used
              when sending link FrameLossMeasurementMsg."
     ::= { wwpLeosCfmFrameLossMsgEntry 4 }
 
 wwpLeosCfmFrameLossMsgPriority OBJECT-TYPE
     SYNTAX       INTEGER (0..7)
     MAX-ACCESS   read-create
     STATUS       obsolete
     DESCRIPTION
             "This object specifies the FrameLossMeasurementMsg priority to be
             used when sending link FrameLossMeasurementMsg."
     ::= { wwpLeosCfmFrameLossMsgEntry 5 }
 
 wwpLeosCfmFrameLossMsgRowStatus OBJECT-TYPE
     SYNTAX       RowStatus
     MAX-ACCESS   read-create
     STATUS       obsolete
     DESCRIPTION
             "Used to manage the creation and deletion of the conceptual rows in this table.
	     To create a row in this table, set this object to 'createAndGo'.
	     To delete a row in this table, set this to 'destroy'.
             If 'destroy' is used and either TargetMacAddr or TargetMEPID is
             specified, a cancel is done for any repeating test on those items."
     ::= { wwpLeosCfmFrameLossMsgEntry 6 } 
     
 wwpLeosCfmFrameLossMsgRepeat OBJECT-TYPE
 	 SYNTAX			INTEGER {
 	 					enable(1),
 	 					disable(2)
 	 					}
 	 MAX-ACCESS		read-create
 	 STATUS			obsolete
 	 DESCRIPTION
 	 		"Used to make the Frame Loss Measurement test a repeating test."
 	 ::= { wwpLeosCfmFrameLossMsgEntry 7 } 
 	 
 wwpLeosCfmFrameLossMsgRepeatCount OBJECT-TYPE
 	SYNTAX			INTEGER (0..1440)
 	MAX-ACCESS		read-create
 	STATUS			obsolete
 	DESCRIPTION
 			"The repeat time in minutes for the Frame Loss Measurement test.
 			If zero is specified, the test runs continuously."
 	::= { wwpLeosCfmFrameLossMsgEntry 8 } 
 	
  wwpLeosCfmFrameLossMsgFlnThreshold OBJECT-TYPE
 	SYNTAX			INTEGER (-1..600)
 	MAX-ACCESS		read-create
 	STATUS			obsolete
 	DESCRIPTION
 			"The fault threshold for the Frame Loss Measurement test.
 			A value of -1 disables the generate of faults. 
			A value of 0 or greater	is compared to the frame loss near result of the
 			test and a fault is generated if the threshold is exceeded."
 	::= { wwpLeosCfmFrameLossMsgEntry 9 }
 
 wwpLeosCfmFrameLossMsgFlfThreshold OBJECT-TYPE
 	SYNTAX			INTEGER (-1..600)
 	MAX-ACCESS		read-create
 	STATUS			obsolete
 	DESCRIPTION
 			"The fault threshold for the Frame Loss Measurement test.
 			A value of -1 disables the generate of faults. 
			A value of 0 or greater is compared to the frame loss far result of the
 			test and a fault is generated if the threshold is exceeded."
 	::= { wwpLeosCfmFrameLossMsgEntry 10 }
 
  --
  --  CFM Remote MEP CCM Loss Table
  --                                   
 wwpLeosCfmRemoteMEPCCMLossTable OBJECT-TYPE
     SYNTAX     SEQUENCE OF WwpLeosCfmRemoteMEPCCMLossEntry
     MAX-ACCESS not-accessible
     STATUS     current
     DESCRIPTION
            "The (conceptual) table listing the display 
             parameters for the Remote MEP CCM Loss table."  
     ::= { wwpLeosCfmRemoteMEPCCMLoss 1 }
                
 wwpLeosCfmRemoteMEPCCMLossEntry OBJECT-TYPE
     SYNTAX      WwpLeosCfmRemoteMEPCCMLossEntry
     MAX-ACCESS  not-accessible
     STATUS      current
     DESCRIPTION
           "An entry (conceptual row) in the wwpLeosCfmRemoteMEPCCMLossTable."
     INDEX {wwpLeosCfmServiceIndex, wwpLeosCfmRemoteMEPID, wwpLeosCfmRemoteMEPCCMLossNum}
     ::= { wwpLeosCfmRemoteMEPCCMLossTable 1 }
                
 WwpLeosCfmRemoteMEPCCMLossEntry ::=  SEQUENCE { 
     wwpLeosCfmRemoteMEPCCMLossNum			Unsigned32,
     wwpLeosCfmRemoteMEPCCMLossCount		Gauge32
 }

 wwpLeosCfmRemoteMEPCCMLossNum OBJECT-TYPE
 	SYNTAX		Unsigned32 (1..96)
 	MAX-ACCESS	not-accessible
 	STATUS		current
 	DESCRIPTION
 			"This object is used as an index into the table and specifies
 			the CCM Loss bucket to be returned."
 	::= { wwpLeosCfmRemoteMEPCCMLossEntry 1 }
 	
 wwpLeosCfmRemoteMEPCCMLossCount OBJECT-TYPE
 	SYNTAX		Gauge32
 	MAX-ACCESS	read-only
 	STATUS		current
 	DESCRIPTION
 			"This object specifies the number of CCM's lost during the
 			wwpLeosCfmServiceCCMLossBucketInterval sample period."
 	::= { wwpLeosCfmRemoteMEPCCMLossEntry 2 }
 
  
  --
  -- Loopback Msg table
  -- 
  wwpLeosCfmExtLoopbackMsgTable OBJECT-TYPE
     SYNTAX     SEQUENCE OF WwpLeosCfmExtLoopbackMsgEntry
     MAX-ACCESS not-accessible
     STATUS     current
     DESCRIPTION
            "The (conceptual) table listing the configuration parameters for the LoopbackMsg.
             The following attributes are required to create a LoopbackMsg:
             -wwpLeosCfmServiceIndex
             -wwpLeosCfmExtLoopbackMsgTargetMEPID or
             -wwpLeosCfmExtLoopbackMsgTargetMacAddr
             -wwpLeosCfmExtLoopbackMsgCount
             -wwpLeosCfmExtLoopbackMsgData
             -wwpLeosCfmExtLoopbackMsgPriority
             -wwpLeosCfmExtLoopbackMsgAction
             -wwpLeosCfmExtLoopbackMsgInterval
             -wwpLeosCfmExtLoopbackMsgTimeout
             -wwpLeosCfmExtLoopbackMsgLoss"  
              
     ::= { wwpLeosCfmExtLoopback 1 }
                
 wwpLeosCfmExtLoopbackMsgEntry OBJECT-TYPE
     SYNTAX      WwpLeosCfmExtLoopbackMsgEntry
     MAX-ACCESS  not-accessible
     STATUS      current
     DESCRIPTION
           "An entry (conceptual row) in the wwpLeosCfmExtLoopbackMsgTable."
     --wwpLeosCfmExtLoopbackMsgLocalMEPID is the new index in place of portId
     INDEX {wwpLeosCfmServiceIndex, wwpLeosCfmExtLoopbackMsgLocalMEPID}
     ::= { wwpLeosCfmExtLoopbackMsgTable 1 }
                
 WwpLeosCfmExtLoopbackMsgEntry ::=  SEQUENCE { 
     wwpLeosCfmExtLoopbackMsgLocalMEPID              Unsigned32,
     wwpLeosCfmExtLoopbackMsgTargetMEPID             Unsigned32,
     wwpLeosCfmExtLoopbackMsgTargetMacAddr           MacAddress,
     wwpLeosCfmExtLoopbackMsgCount                   INTEGER,
     wwpLeosCfmExtLoopbackMsgData                    DisplayString,
     wwpLeosCfmExtLoopbackMsgPriority                INTEGER,   
     wwpLeosCfmExtLoopbackMsgAction                  SendState,
     wwpLeosCfmExtLoopbackMsgInterval                INTEGER,
     wwpLeosCfmExtLoopbackMsgTimeout                 INTEGER, 
     wwpLeosCfmExtLoopbackMsgLoss                    INTEGER     
 }

 wwpLeosCfmExtLoopbackMsgLocalMEPID OBJECT-TYPE
     SYNTAX       Unsigned32 (1..8191)
     MAX-ACCESS   not-accessible
     STATUS       current
     DESCRIPTION
             "This object specifies the loopback local MEPID."
     ::= { wwpLeosCfmExtLoopbackMsgEntry 1 }
 
 wwpLeosCfmExtLoopbackMsgTargetMEPID OBJECT-TYPE
     SYNTAX       Unsigned32 (1..8191)
     MAX-ACCESS   read-create
     STATUS       current
     DESCRIPTION
             "This object specifies the MEPID.
              This object should only be set if wwpLeosCfmExtLoopbackMsgTargetMacAddr
              is not specified else an error is returned."
     ::= { wwpLeosCfmExtLoopbackMsgEntry 2 }
     
 wwpLeosCfmExtLoopbackMsgTargetMacAddr OBJECT-TYPE
     SYNTAX       MacAddress
     MAX-ACCESS   read-create
     STATUS       current
     DESCRIPTION
             "This object specifies the MAC address to be used when sending
              link LoopbackMsg. This object should only be set if
              wwpLeosCfmExtLoopbackMsgTargetMEPID is not specified else an error is returned."
     ::= { wwpLeosCfmExtLoopbackMsgEntry 3 }
     
 wwpLeosCfmExtLoopbackMsgCount OBJECT-TYPE
     SYNTAX       INTEGER (1..3000) 
     MAX-ACCESS   read-create
     STATUS       current
     DESCRIPTION
             "This object specifies the LoopbackMsg count to be used when
              sending link LoopbackMsg. "
     ::= { wwpLeosCfmExtLoopbackMsgEntry 4 }
 
 wwpLeosCfmExtLoopbackMsgData OBJECT-TYPE
     SYNTAX       DisplayString  (SIZE(1..127))
     MAX-ACCESS   read-create
     STATUS       current
     DESCRIPTION                    
             "This object specifies the LoopbackMsg data to be used when
              sending link LoopbackMsg. "
     ::= { wwpLeosCfmExtLoopbackMsgEntry 5 }

 wwpLeosCfmExtLoopbackMsgPriority OBJECT-TYPE
     SYNTAX       INTEGER (0..7)
     MAX-ACCESS   read-create
     STATUS       current
     DESCRIPTION
             "This object specifies the LoopbackMsg priority to be used when
              sending link LoopbackMsg. "
     ::= { wwpLeosCfmExtLoopbackMsgEntry 6 }
     
 wwpLeosCfmExtLoopbackMsgAction OBJECT-TYPE
   SYNTAX       SendState
   MAX-ACCESS   read-create
   STATUS       current
   DESCRIPTION
             "This object represents the action for the message (send, clear or cancel).
             If set to send(1) and if wwpLeosCfmExtLoopbackMsgTargetMacAddr is specified
             then loopbackMsg is sent to remote MAC.
             If set to send(1) and if wwpLeosCfmExtLoopbackMsgTargetMEPID is specified
             then loopbackMsg is sent to remote mepid.
             If set to clear(2) clears mep statistics for given service and mepid.
             If set to cancel(3) returns commit_failed_error."
     ::= { wwpLeosCfmExtLoopbackMsgEntry 7} 
     
 wwpLeosCfmExtLoopbackMsgInterval OBJECT-TYPE
     SYNTAX       INTEGER (10..60000) 
     MAX-ACCESS   read-create
     STATUS       current
     DESCRIPTION
             "This object specifies the LoopbackMsg interval to be used when
              sending link LoopbackMsg. "
     ::= { wwpLeosCfmExtLoopbackMsgEntry 8 }      
 
 wwpLeosCfmExtLoopbackMsgTimeout OBJECT-TYPE
     SYNTAX       INTEGER (2000..10000) 
     MAX-ACCESS   read-create
     STATUS       current
     DESCRIPTION
             "This object specifies the LoopbackMsg timeout to be used when
              sending link LoopbackMsg. "
     ::= { wwpLeosCfmExtLoopbackMsgEntry 9 }
  
 wwpLeosCfmExtLoopbackMsgLoss OBJECT-TYPE
     SYNTAX       INTEGER (1..3000)
     MAX-ACCESS   read-only
     STATUS       current
     DESCRIPTION
             "This object specifies the LoopbackMsg loss count."
     ::= { wwpLeosCfmExtLoopbackMsgEntry 10 }

  --
  --  CFM MEP Table 
  --                                   
 wwpLeosCfmExtMEPTable OBJECT-TYPE
     SYNTAX     SEQUENCE OF WwpLeosCfmExtMEPEntry
     MAX-ACCESS not-accessible
     STATUS     current
     DESCRIPTION
            "The (conceptual) table listing the configuration
            parameters for the CFM MEP table.
            To create entry in this table use SNMP multiple set operation.
            -wwpLeosCfmExtPortId must be specified.
            -wwpLeosCfmExtVlanId must be specified.
            -wwpLeosCfmExtMEPRowStatus must be set to 'CreateAndGo'"

     ::= { wwpLeosCfmExtMEP 1 }
                
 wwpLeosCfmExtMEPEntry OBJECT-TYPE
     SYNTAX      WwpLeosCfmExtMEPEntry
     MAX-ACCESS  not-accessible
     STATUS      current
     DESCRIPTION
           "An entry (conceptual row) in the wwpLeosCfmMEPTable."
     --   wwpLeosCfmExtMEPId is the new index in place of the MEP port
     INDEX {wwpLeosCfmServiceIndex, wwpLeosCfmExtMEPId}
     ::= { wwpLeosCfmExtMEPTable 1 }
                
 WwpLeosCfmExtMEPEntry ::=  SEQUENCE { 
 	 wwpLeosCfmExtMEPId					    Unsigned32, 
 	 wwpLeosCfmExtPortId					    INTEGER,
 	 wwpLeosCfmExtVlanId					    INTEGER,
     wwpLeosCfmExtMEPAdminState                                     INTEGER,        
     wwpLeosCfmExtMEPOperState                                      INTEGER,        
     wwpLeosCfmExtMEPDirection                                      INTEGER,
     wwpLeosCfmExtMEPCCMState            			    INTEGER,
     wwpLeosCfmExtMEPCCMPriority         			    INTEGER,
     wwpLeosCfmExtMEPLTMPriority         			    INTEGER,  
     wwpLeosCfmExtMEPMacAddr                                        MacAddress,
     wwpLeosCfmExtMEPNextLbmSeqNumber                               Counter32,
     wwpLeosCfmExtMEPNextLTMSeqNumber                               Counter32,
     wwpLeosCfmExtMEPRowStatus                                      RowStatus,
     wwpLeosCfmExtMEPDMMDelay										Counter32,
     wwpLeosCfmExtMEPDMMJitter										Counter32,
     wwpLeosCfmExtMEPLMMFrameLossNear								Counter32,
     wwpLeosCfmExtMEPLMMFrameLossFar								Counter32,
     wwpLeosCfmExtMEPServiceName									DisplayString,
     wwpLeosCfmExtMEPInterfaceName									DisplayString,
     wwpLeosCfmExtMEPServiceInstanceName							DisplayString,
     wwpLeosCfmExtMEPLogicalPortName								DisplayString,
     wwpLeosCfmExtMEPTagMode										INTEGER,
     wwpLeosCfmExtMEPTagVID											INTEGER,
     wwpLeosCfmExtMEPTagPriority									INTEGER,
     wwpLeosCfmExtMEPLMMBadSequence									Counter32,
     wwpLeosCfmExtMEPCCMComment										DisplayString,
     wwpLeosCfmExtMEPLMMMissingSequence								Counter32,
     wwpLeosCfmExtMEPBlockOppositeFaultCurrent						Counter32,
     wwpLeosCfmExtMEPBlockOppositeFaultThreshold					Unsigned32,
     wwpLeosCfmExtMEPBlockOppositeFaultTime							INTEGER,
     wwpLeosCfmExtMEPDMMMinDelay									Counter32,
     wwpLeosCfmExtMEPDMMMaxDelay									Counter32,
     wwpLeosCfmExtMEPDMMMinJitter									Counter32,
     wwpLeosCfmExtMEPDMMMaxJitter									Counter32,
     wwpLeosCfmExtMEPAccelerated									TruthValue,
     wwpLeosCfmExtMEPSLMFrameLossNear								Counter32,
     wwpLeosCfmExtMEPSLMFrameLossFar								Counter32,
     wwpLeosCfmExtMEPDMMTotalJitter									Counter64,
     wwpLeosCfmExtMEPDMMForwardMinJitter							Counter32,
     wwpLeosCfmExtMEPDMMForwardMaxJitter							Counter32,
     wwpLeosCfmExtMEPDMMForwardAveJitter							Counter32,
     wwpLeosCfmExtMEPDMMForwardTotalJitter							Counter64,
     wwpLeosCfmExtMEPDMMBackwardMinJitter							Counter32,
     wwpLeosCfmExtMEPDMMBackwardMaxJitter							Counter32,
     wwpLeosCfmExtMEPDMMBackwardAveJitter							Counter32,
     wwpLeosCfmExtMEPDMMBackwardTotalJitter							Counter64,
     wwpLeosCfmExtMEPSLMFrameDeliveryRatio							CfmFrameRatio,
     wwpLeosCfmExtMEPDMMSuspect										TruthValue,
     wwpLeosCfmExtMEPSLMSuspect										TruthValue,
     wwpLeosCfmExtMEPCSFEnable										INTEGER,
     wwpLeosCfmExtMEPCSFPriority									INTEGER,
     wwpLeosCfmExtMEPCSFTxFaultType									INTEGER,
     wwpLeosCfmExtMEPCSFRxFaultType									INTEGER,
     wwpLeosCfmExtMEPSignalDegradeMonitoringStatus					INTEGER,
     wwpLeosCfmExtMEPSignalDegradeTriggerMode						INTEGER,
     wwpLeosCfmExtMEPSLMTwoWayFrameLoss								Counter32,
     wwpLeosCfmExtMEPSLMTwoWayFrameLossRatio						CfmFrameRatio,
     wwpLeosCfmExtMEPDMMForwardMinDelay								Integer32,
     wwpLeosCfmExtMEPDMMForwardAveDelay								Integer32,
     wwpLeosCfmExtMEPDMMForwardMaxDelay								Integer32,
     wwpLeosCfmExtMEPDMMBackwardMinDelay							Integer32,
     wwpLeosCfmExtMEPDMMBackwardAveDelay							Integer32,
     wwpLeosCfmExtMEPDMMBackwardMaxDelay							Integer32,
     wwpLeosCfmExtMEPLagMemberPortId    							Unsigned32
	}
   
 wwpLeosCfmExtMEPId OBJECT-TYPE
     SYNTAX      Unsigned32 (1..8191)
     MAX-ACCESS  accessible-for-notify
     STATUS      current
     DESCRIPTION
             "This is used as the index in the table. This object specifies the MEP id for the given service."
     ::= { wwpLeosCfmExtMEPEntry 1 } 
     
 wwpLeosCfmExtPortId OBJECT-TYPE
     SYNTAX  INTEGER (1..65535)
     MAX-ACCESS read-create
     STATUS current
     DESCRIPTION 
     	""
     ::= { wwpLeosCfmExtMEPEntry 2 }
    
 wwpLeosCfmExtVlanId OBJECT-TYPE
    SYNTAX INTEGER  (0..4094)
    MAX-ACCESS read-create
    STATUS current
    DESCRIPTION
    	""
    ::= { wwpLeosCfmExtMEPEntry 3 }

 wwpLeosCfmExtMEPAdminState OBJECT-TYPE
     SYNTAX      INTEGER   {
                                disabled(1),
                                enabled(2)  
                          }
     MAX-ACCESS  read-write
     STATUS      current
     DESCRIPTION
             "This object specifies the admin state of CFM MEP."
     ::= { wwpLeosCfmExtMEPEntry 4 }
 
 wwpLeosCfmExtMEPOperState OBJECT-TYPE
     SYNTAX      INTEGER   {
                                disabled(1),
                                enabled(2)  
                          }
     MAX-ACCESS  read-only
     STATUS      current
     DESCRIPTION
             "This object specifies the oper state of CFM MEP."
     ::= { wwpLeosCfmExtMEPEntry 5 }
     
 wwpLeosCfmExtMEPDirection OBJECT-TYPE
     SYNTAX      INTEGER {
                                up(1),
                                down(2)
                         }
     MAX-ACCESS  read-create
     STATUS      current
     DESCRIPTION
             "This object specifies the MEP direction of the service.
              This object can only be set if wwpLeosCfmServiceIndex is of type VLAN."
     ::= { wwpLeosCfmExtMEPEntry 6 } 
 
 wwpLeosCfmExtMEPCCMState OBJECT-TYPE
     SYNTAX       INTEGER {
                                on(1),
                                off(2)
                                }
     MAX-ACCESS   read-write
     STATUS       current
     DESCRIPTION
             "This object specifies the CCM transmission for the service specified by wwpLeosCfmServiceType."
     ::= { wwpLeosCfmExtMEPEntry 7 }
     
 wwpLeosCfmExtMEPCCMPriority OBJECT-TYPE
     SYNTAX       INTEGER (0..7)
     MAX-ACCESS   read-write
     STATUS       current
     DESCRIPTION
             "This object specifies the priority of CCM messages transmitted."
     ::= { wwpLeosCfmExtMEPEntry 8 }
     
 wwpLeosCfmExtMEPLTMPriority OBJECT-TYPE
     SYNTAX      INTEGER (0..7)
     MAX-ACCESS  read-write
     STATUS      current
     DESCRIPTION
             "This object specifies the priority received on the given service and MEP."
     DEFVAL {7}
     ::= { wwpLeosCfmExtMEPEntry 9 } 
     
   
 wwpLeosCfmExtMEPMacAddr OBJECT-TYPE
     SYNTAX      MacAddress
     MAX-ACCESS  read-only
     STATUS      current
     DESCRIPTION
             "This object specifies the MAC address received on the given service and MEP."
     ::= { wwpLeosCfmExtMEPEntry 10 }
     
 wwpLeosCfmExtMEPNextLbmSeqNumber OBJECT-TYPE
     SYNTAX      Counter32 
     MAX-ACCESS  read-only
     STATUS      current
     DESCRIPTION
             "This object specifies the next lbm sequence number received on the given service and MEP."
     ::= { wwpLeosCfmExtMEPEntry 11 }
     
      
 wwpLeosCfmExtMEPNextLTMSeqNumber OBJECT-TYPE
     SYNTAX      Counter32 
     MAX-ACCESS  read-only
     STATUS      current
     DESCRIPTION
             "This object specifies the next LTM sequence number received on the given service and MEP."
     ::= { wwpLeosCfmExtMEPEntry 12 }
     
      
 wwpLeosCfmExtMEPRowStatus OBJECT-TYPE
     SYNTAX       RowStatus
     MAX-ACCESS   read-create
     STATUS       current
     DESCRIPTION
             "Used to manage the creation and deletion of the conceptual rows in this table.
	     To create a row in this table, set this object to 'createAndGo'.
	     To delete a row in this table, set this to 'destroy'."
     ::= { wwpLeosCfmExtMEPEntry 13 }  
        
 wwpLeosCfmExtMEPDMMDelay OBJECT-TYPE
     SYNTAX      Counter32
     MAX-ACCESS  read-only
     STATUS      current
     DESCRIPTION
             "This object specifies the average delay in microseconds measured during
             the last DMM performance test on the given service and MEP."
     ::= { wwpLeosCfmExtMEPEntry 14 } 
     
 wwpLeosCfmExtMEPDMMJitter OBJECT-TYPE
     SYNTAX      Counter32
     MAX-ACCESS  read-only
     STATUS      current
     DESCRIPTION
             "This object specifies the average jitter in microseconds measured during
             the last DMM performance test on the given service and MEP."
     ::= { wwpLeosCfmExtMEPEntry 15 } 
     
 wwpLeosCfmExtMEPLMMFrameLossNear OBJECT-TYPE
     SYNTAX      Counter32
     MAX-ACCESS  read-only
     STATUS      current
     DESCRIPTION
             "This object specifies the number of lost frames on the near side measured during
             the last LMM performance test on the given service and MEP."
     ::= { wwpLeosCfmExtMEPEntry 16 } 
     
 wwpLeosCfmExtMEPLMMFrameLossFar OBJECT-TYPE
     SYNTAX      Counter32
     MAX-ACCESS  read-only
     STATUS      current
     DESCRIPTION
             "This object specifies the number of lost frames on the far side measured during
             the last LMM performance test on the given service and MEP."
     ::= { wwpLeosCfmExtMEPEntry 17 }   
 
 wwpLeosCfmExtMEPServiceName OBJECT-TYPE
     SYNTAX      DisplayString (SIZE(1..41))
     MAX-ACCESS  read-only
     STATUS      current
     DESCRIPTION
             "This object specifies the service name assigned to this MEP."
     ::= { wwpLeosCfmExtMEPEntry 50 } 
 
 wwpLeosCfmExtMEPInterfaceName	OBJECT-TYPE
     SYNTAX		DisplayString	(SIZE(1..31))
     MAX-ACCESS	 read-only
     STATUS		  current
     DESCRIPTION
     	     "This object specifies the interface name associated with this MEP."
     ::= { wwpLeosCfmExtMEPEntry	51 }
 
 wwpLeosCfmExtMEPServiceInstanceName	OBJECT-TYPE
     SYNTAX		DisplayString	(SIZE(1..31))
     MAX-ACCESS	 read-only
     STATUS		  current
     DESCRIPTION
     	     "This object specifies the service instance name associated with this MEP."
     ::= { wwpLeosCfmExtMEPEntry	52 }
 
 wwpLeosCfmExtMEPLogicalPortName		OBJECT-TYPE
 	 SYNTAX		DisplayString	(SIZE(1..31))
 	 MAX-ACCESS		read-only
 	 STATUS			current
 	 DESCRIPTION
 	     "This object specifies the logical port name associated with this MEP."
 	 ::= { wwpLeosCfmExtMEPEntry	53 }  
  
  wwpLeosCfmExtMEPTagMode  OBJECT-TYPE
 	 SYNTAX		INTEGER {
 	 				on(1),
 	 				off(2)
 	 			}
 	 MAX-ACCESS		read-write
 	 STATUS			current
 	 DESCRIPTION
 	 "This object specifies the tag-mode for the given mep and service. 
	 When on(1) the MEP originates all frames with an additional inner-most tag. 
	 On a down MEP this is the CVLAN tag."
 	 DEFVAL {off}
 	 ::= { wwpLeosCfmExtMEPEntry	54 }  

  wwpLeosCfmExtMEPTagVID OBJECT-TYPE
 	 SYNTAX		INTEGER ( 0..4095)
 	 MAX-ACCESS		read-write
 	 STATUS			current
 	 DESCRIPTION
 	 "This object specifies the VLAN ID for the additional tag given mep and service."
 	 DEFVAL {0}
 	 ::= { wwpLeosCfmExtMEPEntry	55 }
 	 
   wwpLeosCfmExtMEPTagPriority OBJECT-TYPE
 	 SYNTAX		INTEGER (0..7)
 	 MAX-ACCESS		read-write
 	 STATUS			current
 	 DESCRIPTION
 	   "This object specifies the priority encoded in the additional tag."
 	 DEFVAL {7}
 	 ::= { wwpLeosCfmExtMEPEntry	56 }
	
   wwpLeosCfmExtMEPLMMBadSequence OBJECT-TYPE
     SYNTAX      Counter32
     MAX-ACCESS  read-only
     STATUS      current
     DESCRIPTION
             "This object specifes the number of frames with bad sequence numbers
             measured during the last LMM performance test on the given service and MEP."
     ::= { wwpLeosCfmExtMEPEntry 57 }

 wwpLeosCfmExtMEPCCMComment OBJECT-TYPE
     SYNTAX       DisplayString (SIZE(1..32))
     MAX-ACCESS   read-create
     STATUS       current
     DESCRIPTION
             "This object allows the user to set the MEP CCM comment."
     ::= { wwpLeosCfmExtMEPEntry 58 }
 
 wwpLeosCfmExtMEPLMMMissingSequence   OBJECT-TYPE
 	 SYNTAX      Counter32
     MAX-ACCESS  read-only
     STATUS      current
     DESCRIPTION
             "This object specifies the number of frames with missing sequence numbers
             measured during the last LMM performance test on the given service and MEP."
     ::= { wwpLeosCfmExtMEPEntry 59 }
 
 wwpLeosCfmExtMEPBlockOppositeFaultCurrent OBJECT-TYPE
     SYNTAX       Counter32
     MAX-ACCESS   read-only
     STATUS       current
     DESCRIPTION  
        "This object specifies the number of frames seen in the current sample window."
     ::= { wwpLeosCfmExtMEPEntry 60 }
 
 wwpLeosCfmExtMEPBlockOppositeFaultThreshold OBJECT-TYPE
     SYNTAX       Unsigned32
     MAX-ACCESS   read-write
     STATUS       current
     DESCRIPTION  
        "This object specifies the number of frames to block before generating a fault."
     ::= { wwpLeosCfmExtMEPEntry 61 }
 
 wwpLeosCfmExtMEPBlockOppositeFaultTime OBJECT-TYPE
     SYNTAX       INTEGER (1..3600)
     MAX-ACCESS   read-write
     STATUS       current
     DESCRIPTION  "This object specifies the frame sample window size in minutes."
     ::= { wwpLeosCfmExtMEPEntry 62 }
        
 wwpLeosCfmExtMEPDMMMinDelay OBJECT-TYPE
     SYNTAX      Counter32
     MAX-ACCESS  read-only
     STATUS      current
     DESCRIPTION
             "This object specifies the minimum delay in microseconds measured during
             the last DMM performance test on the given service and MEP."
     ::= { wwpLeosCfmExtMEPEntry 63 } 
        
 wwpLeosCfmExtMEPDMMMaxDelay OBJECT-TYPE
     SYNTAX      Counter32
     MAX-ACCESS  read-only
     STATUS      current
     DESCRIPTION
             "This object specifies the maximum delay in microseconds measured during
             the last DMM performance test on the given service and MEP."
     ::= { wwpLeosCfmExtMEPEntry 64 } 
     
 wwpLeosCfmExtMEPDMMMinJitter OBJECT-TYPE
     SYNTAX      Counter32
     MAX-ACCESS  read-only
     STATUS      current
     DESCRIPTION
             "This object specifies the minimum jitter in microseconds measured during
             the last DMM performance test on the given service and MEP."
     ::= { wwpLeosCfmExtMEPEntry 65 }
     
 wwpLeosCfmExtMEPDMMMaxJitter OBJECT-TYPE
     SYNTAX      Counter32
     MAX-ACCESS  read-only
     STATUS      current
     DESCRIPTION
             "This object specifies the maximum jitter in microseconds measured during
             the last DMM performance test on the given service and MEP."
     ::= { wwpLeosCfmExtMEPEntry 66 }

 wwpLeosCfmExtMEPAccelerated OBJECT-TYPE
     SYNTAX      TruthValue
     MAX-ACCESS  read-only
     STATUS      current
     DESCRIPTION
             "This object specifies if the MEP is monitored in hardware."
     ::= { wwpLeosCfmExtMEPEntry 67 }             
     
 wwpLeosCfmExtMEPSLMFrameLossNear OBJECT-TYPE
     SYNTAX      Counter32
     MAX-ACCESS  read-only
     STATUS      current
     DESCRIPTION
             "This object specifies the number of lost frames on the near side measured during
             the last SLM performance test on the given service and MEP."
     ::= { wwpLeosCfmExtMEPEntry 68 } 
     
 wwpLeosCfmExtMEPSLMFrameLossFar OBJECT-TYPE
     SYNTAX      Counter32
     MAX-ACCESS  read-only
     STATUS      current
     DESCRIPTION
             "This object specifies the number of lost frames on the far side measured during
             the last SLM performance test on the given service and MEP."
     ::= { wwpLeosCfmExtMEPEntry 69 } 

 wwpLeosCfmExtMEPDMMTotalJitter OBJECT-TYPE
     SYNTAX      Counter64
     MAX-ACCESS  read-only
     STATUS      current
     DESCRIPTION
             "This object specifies the total jitter in microseconds measured during
             the last DMM performance test on the given service and MEP."
     ::= { wwpLeosCfmExtMEPEntry 70 } 

 wwpLeosCfmExtMEPDMMForwardMinJitter OBJECT-TYPE
     SYNTAX      Counter32
     MAX-ACCESS  read-only
     STATUS      current
     DESCRIPTION
             "This object specifies the minimum jitter in microseconds measured during
             the last DMM performance test on the given service and MEP in forward direction."
     ::= { wwpLeosCfmExtMEPEntry 71 }
     
 wwpLeosCfmExtMEPDMMForwardMaxJitter OBJECT-TYPE
     SYNTAX      Counter32
     MAX-ACCESS  read-only
     STATUS      current
     DESCRIPTION
             "This object specifies the maximum jitter in microseconds measured during
             the last DMM performance test on the given service and MEP in forward direction."
     ::= { wwpLeosCfmExtMEPEntry 72 }

 wwpLeosCfmExtMEPDMMForwardAveJitter OBJECT-TYPE
     SYNTAX      Counter32
     MAX-ACCESS  read-only
     STATUS      current
     DESCRIPTION
             "This object specifies the average jitter in microseconds measured during
             the last DMM performance test on the given service and MEP in forward direction."
     ::= { wwpLeosCfmExtMEPEntry 73 } 

 wwpLeosCfmExtMEPDMMForwardTotalJitter OBJECT-TYPE
     SYNTAX      Counter64
     MAX-ACCESS  read-only
     STATUS      current
     DESCRIPTION
             "This object specifies the total jitter in microseconds measured during
             the last DMM performance test on the given service and MEP in forward direction."
     ::= { wwpLeosCfmExtMEPEntry 74 } 

 wwpLeosCfmExtMEPDMMBackwardMinJitter OBJECT-TYPE
     SYNTAX      Counter32
     MAX-ACCESS  read-only
     STATUS      current
     DESCRIPTION
             "This object specifies the minimum jitter in microseconds measured during
             the last DMM performance test on the given service and MEP in backward direction."
     ::= { wwpLeosCfmExtMEPEntry 75 }
     
 wwpLeosCfmExtMEPDMMBackwardMaxJitter OBJECT-TYPE
     SYNTAX      Counter32
     MAX-ACCESS  read-only
     STATUS      current
     DESCRIPTION
             "This object specifies the maximum jitter in microseconds measured during
             the last DMM performance test on the given service and MEP in backward direction."
     ::= { wwpLeosCfmExtMEPEntry 76 }

 wwpLeosCfmExtMEPDMMBackwardAveJitter OBJECT-TYPE
     SYNTAX      Counter32
     MAX-ACCESS  read-only
     STATUS      current
     DESCRIPTION
             "This object specifies the average jitter in microseconds measured during
             the last DMM performance test on the given service and MEP in backward direction."
     ::= { wwpLeosCfmExtMEPEntry 77 } 

 wwpLeosCfmExtMEPDMMBackwardTotalJitter OBJECT-TYPE
     SYNTAX      Counter64
     MAX-ACCESS  read-only
     STATUS      current
     DESCRIPTION
             "This object specifies the total jitter in microseconds measured during
             the last DMM performance test on the given service and MEP in backward direction."
     ::= { wwpLeosCfmExtMEPEntry 78 } 

 wwpLeosCfmExtMEPSLMFrameDeliveryRatio OBJECT-TYPE
     SYNTAX          CfmFrameRatio
     MAX-ACCESS      read-only
     STATUS          current
     DESCRIPTION
             "This object specifies the Frame Delivery Ratio as percentage of total number of SLR frames received
              divided by total number of SLM frames sent in the last iteration of the completed test."
     ::= { wwpLeosCfmExtMEPEntry 79 } 

 wwpLeosCfmExtMEPDMMSuspect OBJECT-TYPE
     SYNTAX          TruthValue
     MAX-ACCESS      read-only
     STATUS          current
     DESCRIPTION
             "This object indicates that there is discontinuity in DMM Performance Measurement.
              Condition for discontinuity include:
              a) The conducting of performance measurement is halted before the current measurement interval is completed."
     ::= { wwpLeosCfmExtMEPEntry 80 } 

 wwpLeosCfmExtMEPSLMSuspect OBJECT-TYPE
     SYNTAX          TruthValue
     MAX-ACCESS      read-only
     STATUS          current
     DESCRIPTION
             "This object indicates that there is discontinuity in SLM Performance Measurement.
              Condition for discontinuity include:
              a) The conducting of performance measurement is halted before the current measurement interval is completed."
     ::= { wwpLeosCfmExtMEPEntry 81 } 

 wwpLeosCfmExtMEPCSFEnable OBJECT-TYPE
     SYNTAX       INTEGER {
                            on(1),
                            off(2)
                          }
     MAX-ACCESS   read-only
     STATUS       current
     DESCRIPTION
             "This object specifies the CSF Functionality admin enabled/disabled for the MEP."
     DEFVAL       {off}
     ::= { wwpLeosCfmExtMEPEntry 82 }
     
 wwpLeosCfmExtMEPCSFPriority OBJECT-TYPE
     SYNTAX       INTEGER (0..7)
     MAX-ACCESS   read-only
     STATUS       current
     DESCRIPTION
             "This object specifies the priority of CSF messages transmitted."
     DEFVAL {7}
     ::= { wwpLeosCfmExtMEPEntry 83 }

  wwpLeosCfmExtMEPCSFTxFaultType OBJECT-TYPE
     SYNTAX       INTEGER {
                            los(0),
                            fdi(1),
                            rdi(2),
                            dci(3)
                          }
     MAX-ACCESS   read-only
     STATUS       current
     DESCRIPTION
             "This object specifies the CSF Tx Fault Type. If no CSF packet is transmitted then Fault Type is Dci. Default is also Dci."
     DEFVAL       {dci}
     ::= { wwpLeosCfmExtMEPEntry 84 }
    
  wwpLeosCfmExtMEPCSFRxFaultType OBJECT-TYPE
     SYNTAX       INTEGER {
                            los(0),
                            fdi(1),
                            rdi(2),
                            dci(3)
                          }
     MAX-ACCESS   read-only
     STATUS       current
     DESCRIPTION
             "This object specifies the CSF Rx Fault Type. If no CSF packet is received then Fault Type is Dci. Default is also Dci."
     DEFVAL       {dci}
     ::= { wwpLeosCfmExtMEPEntry 85 }

  wwpLeosCfmExtMEPSignalDegradeMonitoringStatus OBJECT-TYPE
     SYNTAX       INTEGER {
                            off(1),
                            on(2)
                          }
     MAX-ACCESS   read-create
     STATUS       current
     DESCRIPTION
             "This object enables/disables signal degrade monitoring on the mep."
     DEFVAL       {off}
     ::= { wwpLeosCfmExtMEPEntry 86 }

  wwpLeosCfmExtMEPSignalDegradeTriggerMode OBJECT-TYPE
     SYNTAX       INTEGER {
                            nearEnd(1),
                            nearFarEnd(2)
                          }
     MAX-ACCESS   read-create
     STATUS       current
     DESCRIPTION
             "This object sets the signal degrade trigger mode on the mep.
              nearEnd: In this mode, near end frame loss shall be compared with wwpLeosCfmExtSynLossSessionSdSetThreshold and 
              wwpLeosCfmExtSynLossSessionSdClearThreshold.
              nearFarEnd: In this mode, both near end and far end frame loss shall be compared with wwpLeosCfmExtSynLossSessionSdSetThreshold
              and wwpLeosCfmExtSynLossSessionSdClearThreshold."
     DEFVAL       {nearEnd}
     ::= { wwpLeosCfmExtMEPEntry 87 }

  wwpLeosCfmExtMEPSLMTwoWayFrameLoss OBJECT-TYPE
     SYNTAX      Counter32
     MAX-ACCESS  read-only
     STATUS      current
     DESCRIPTION
             "This object specifies the number of lost frames for the round trip measured during
             the last SLM performance test on the given service and MEP."
     ::= { wwpLeosCfmExtMEPEntry 88 } 

 wwpLeosCfmExtMEPSLMTwoWayFrameLossRatio OBJECT-TYPE
     SYNTAX          CfmFrameRatio
     MAX-ACCESS      read-only
     STATUS          current
     DESCRIPTION
             "This object specifies the Frame Loss Ratio as percentage of difference of SLM frames sent and SLR 
              frames received divided by total number of SLM frames sent in the last iteration of the completed test."
     ::= { wwpLeosCfmExtMEPEntry 89 } 

wwpLeosCfmExtMEPDMMForwardMinDelay OBJECT-TYPE
     SYNTAX      Integer32
     MAX-ACCESS  read-only
     STATUS      current
     DESCRIPTION
             "This object specifies the minimum delay in microseconds measured during
             the last DMM performance test on the given service and MEP in forward direction."
     ::= { wwpLeosCfmExtMEPEntry 90 }

wwpLeosCfmExtMEPDMMForwardAveDelay OBJECT-TYPE
     SYNTAX      Integer32
     MAX-ACCESS  read-only
     STATUS      current
     DESCRIPTION
             "This object specifies the average delay in microseconds measured during
             the last DMM performance test on the given service and MEP in forward direction."
     ::= { wwpLeosCfmExtMEPEntry 91 }

wwpLeosCfmExtMEPDMMForwardMaxDelay OBJECT-TYPE
     SYNTAX      Integer32
     MAX-ACCESS  read-only
     STATUS      current
     DESCRIPTION
             "This object specifies the maximum delay in microseconds measured during
             the last DMM performance test on the given service and MEP in forward direction."
     ::= { wwpLeosCfmExtMEPEntry 92 }

wwpLeosCfmExtMEPDMMBackwardMinDelay OBJECT-TYPE
     SYNTAX      Integer32
     MAX-ACCESS  read-only
     STATUS      current
     DESCRIPTION
             "This object specifies the minimum delay in microseconds measured during
             the last DMM performance test on the given service and MEP in backward direction."
     ::= { wwpLeosCfmExtMEPEntry 93 }

wwpLeosCfmExtMEPDMMBackwardAveDelay OBJECT-TYPE
     SYNTAX      Integer32
     MAX-ACCESS  read-only
     STATUS      current
     DESCRIPTION
             "This object specifies the average delay in microseconds measured during
             the last DMM performance test on the given service and MEP in backward direction."
     ::= { wwpLeosCfmExtMEPEntry 94 }

wwpLeosCfmExtMEPDMMBackwardMaxDelay OBJECT-TYPE
     SYNTAX      Integer32
     MAX-ACCESS  read-only
     STATUS      current
     DESCRIPTION
             "This object specifies the maximum delay in microseconds measured during
             the last DMM performance test on the given service and MEP in backward direction."
     ::= { wwpLeosCfmExtMEPEntry 95 }

wwpLeosCfmExtMEPLagMemberPortId OBJECT-TYPE
    SYNTAX       Unsigned32 (0..65535)
    MAX-ACCESS   read-create
    STATUS       current
    DESCRIPTION 
    	     "This object specifies the LAG member port on which MEP is created.
              Default value indicates that the MEP is not created on LAG member port."
    DEFVAL       {0}
    ::= { wwpLeosCfmExtMEPEntry 96 }  

--
-- CFM MEP Statistics
--
   
 wwpLeosCfmExtMEPStatsTable OBJECT-TYPE
     SYNTAX     SEQUENCE OF WwpLeosCfmExtMEPStatsEntry
     MAX-ACCESS not-accessible
     STATUS     current
     DESCRIPTION
            "The (conceptual) table listing the configuration
            parameters for the CFM MEP table."  
     ::= { wwpLeosCfmExtMEP 2 }
                
 wwpLeosCfmExtMEPStatsEntry OBJECT-TYPE
     SYNTAX      WwpLeosCfmExtMEPStatsEntry
     MAX-ACCESS  not-accessible
     STATUS      current
     DESCRIPTION
           "An entry (conceptual row) in the wwpLeosCfmMEPTable."
     --   wwpLeosCfmExtMEPId is the new index in place of mepport
     INDEX {wwpLeosCfmServiceIndex, wwpLeosCfmExtMEPId}
     ::= { wwpLeosCfmExtMEPStatsTable 1 }   
 
  WwpLeosCfmExtMEPStatsEntry ::=  SEQUENCE { 
 	 wwpLeosCfmExtMEPStatsTotalValidFramesReceived								 Counter64, 
 	 wwpLeosCfmExtMEPStatsTotalInvalidFramesReceived							 Counter64,
 	 wwpLeosCfmExtMEPStatsTotalInvalidMessageOverflowReceived					 Counter64,
     wwpLeosCfmExtMEPStatsInvalidPortStatusTLVReceived                           Counter64,        
     wwpLeosCfmExtMEPStatsInvalidInterfaceStatusTLVReceived                      Counter64,        
     wwpLeosCfmExtMEPStatsInvalidSenderIDTLVReceived                             Counter64,
     wwpLeosCfmExtMEPStatsCCMTxmt            									 Counter64,
     wwpLeosCfmExtMEPStatsValidCCMReceived         								 Counter64,
     wwpLeosCfmExtMEPStatsCCMInSequenceReceived         						 Counter64,  
     wwpLeosCfmExtMEPStatsCCMSequenceErrorsReceived                              Counter64,
     wwpLeosCfmExtMEPStatsMDLevelXconCCMReceived                                 Counter64,
     wwpLeosCfmExtMEPStatsMAIDXconCCMReceived                                    Counter64,
     wwpLeosCfmExtMEPStatsIntervalErrorCCMReceived                               Counter64,
     wwpLeosCfmExtMEPStatsRxInvalidCCM											Counter64,
     wwpLeosCfmExtMEPStatsLBMTxmt												Counter64,
     wwpLeosCfmExtMEPStatsLBRTxmt												Counter64,
     wwpLeosCfmExtMEPStatsInOrderLBRReceived									Counter64, 
     wwpLeosCfmExtMEPStatsOutOfOrderLBRReceived									Counter64,
     wwpLeosCfmExtMEPStatsContentMismatchLBRReceived							Counter64,
     wwpLeosCfmExtMEPStatsUnexpectedLBRReceived									Counter64,
     wwpLeosCfmExtMEPStatsInvalidLBRReceived									Counter64,
     wwpLeosCfmExtMEPStatsLTMTxmt												Counter64,
     wwpLeosCfmExtMEPStatsValidLTMReceived										Counter64,
     wwpLeosCfmExtMEPStatsTotalInvalidLTMReceived								Counter64,
     wwpLeosCfmExtMEPStatsInvalidLTRAction										Counter64,
     wwpLeosCfmExtMEPStatsLTRTxmt												Counter64,
     wwpLeosCfmExtMEPStatsLTRReceived											Counter64,
     wwpLeosCfmExtMEPStatsDMMTxmt												Counter64,
     wwpLeosCfmExtMEPStatsDMMReceived											Counter64,
     wwpLeosCfmExtMEPStatsDMRTxmt												Counter64,
     wwpLeosCfmExtMEPStatsDMRReceived											Counter64,
     wwpLeosCfmExtMEPStatsDMReplyTimeout										Counter64,
     wwpLeosCfmExtMEPStatsLMMTxmt												Counter64,
     wwpLeosCfmExtMEPStatsLMMReceived											Counter64,
     wwpLeosCfmExtMEPStatsLMRTxmt												Counter64,
     wwpLeosCfmExtMEPStatsLMRReceived											Counter64,
     wwpLeosCfmExtMEPStatsLMRTimeout											Counter64,
     wwpLeosCfmExtMEPStatsMepIdErrorCCMReceived									Counter64,
     wwpLeosCfmExtMEPStatsClear													INTEGER,
     wwpLeosCfmExtMEPStatsValidLBMReceived 										Counter64,
     wwpLeosCfmExtMEPStatsInvalidLBMReceived                                    Counter64,
     wwpLeosCfmExtMEPStatsUnexpectedLTRReceived									Counter64,
     wwpLeosCfmExtMEPStatsInvalidDMMReceived									Counter64,
     wwpLeosCfmExtMEPStatsInvalidDMRReceived									Counter64,
     wwpLeosCfmExtMEPStatsUnexpectedDMRReceived									Counter64,
     wwpLeosCfmExtMEPStatsInvalidLMMReceived                                   	Counter64,
 	 wwpLeosCfmExtMEPStatsInvalidLMRReceived                                 	Counter64,
 	 wwpLeosCfmExtMEPStatsInvalidBlockedOppositeMep								Counter64,
 	 wwpLeosCfmExtMEPStatsSLMTxmt												Counter64,
     wwpLeosCfmExtMEPStatsSLMReceived											Counter64,
     wwpLeosCfmExtMEPStatsSLRTxmt												Counter64,
     wwpLeosCfmExtMEPStatsSLRReceived											Counter64,
     wwpLeosCfmExtMEPStatsSLRTimeout											Counter64,
     wwpLeosCfmExtMEPStatsInvalidSLMReceived                                    Counter64,
     wwpLeosCfmExtMEPStatsInvalidSLRReceived                                    Counter64,
     wwpLeosCfmExtMEPStatsTotalCSFTxmt                                          Counter64,
     wwpLeosCfmExtMEPStatsCSFLosTxmt                                            Counter64,
     wwpLeosCfmExtMEPStatsCSFDciTxmt                                            Counter64,
     wwpLeosCfmExtMEPStatsValidCSFReceived                                      Counter64,
     wwpLeosCfmExtMEPStatsCSFLosReceived                                        Counter64,
     wwpLeosCfmExtMEPStatsCSFDciReceived                                        Counter64,
     wwpLeosCfmExtMEPStatsInvalidCSFReceived                                    Counter64
  }
 wwpLeosCfmExtMEPStatsTotalValidFramesReceived	OBJECT-TYPE
 	SYNTAX Counter64
 	MAX-ACCESS  read-only
     STATUS      current
     DESCRIPTION
             "This object specifies the total valid frames received."
     ::= { wwpLeosCfmExtMEPStatsEntry 1 }  
     
 wwpLeosCfmExtMEPStatsTotalInvalidFramesReceived  OBJECT-TYPE
 	SYNTAX Counter64
 	MAX-ACCESS  read-only
     STATUS      current
     DESCRIPTION
             "This object specifies the total invalid frames received."
     ::= { wwpLeosCfmExtMEPStatsEntry 2 }           
     
 wwpLeosCfmExtMEPStatsTotalInvalidMessageOverflowReceived  OBJECT-TYPE
 	SYNTAX Counter64
 	MAX-ACCESS  read-only
     STATUS      current
     DESCRIPTION
             "This object specifies the total invalid message overflow frames received "
     ::= { wwpLeosCfmExtMEPStatsEntry 3 }
 
 wwpLeosCfmExtMEPStatsInvalidPortStatusTLVReceived  OBJECT-TYPE
 	SYNTAX Counter64
 	MAX-ACCESS  read-only
     STATUS      current
     DESCRIPTION
             "This object specifies the total invalid port status TLVs received."
     ::= { wwpLeosCfmExtMEPStatsEntry 4 } 
 
 wwpLeosCfmExtMEPStatsInvalidInterfaceStatusTLVReceived  OBJECT-TYPE
 	SYNTAX Counter64
 	MAX-ACCESS  read-only
     STATUS      current
     DESCRIPTION
             "This object specifies the total invalid interface status TLVs received."
     ::= { wwpLeosCfmExtMEPStatsEntry 5 }
  
  wwpLeosCfmExtMEPStatsInvalidSenderIDTLVReceived  OBJECT-TYPE
 	SYNTAX Counter64
 	MAX-ACCESS  read-only
     STATUS      current
     DESCRIPTION
             "This object specifies the total invalid senderID frames received."
     ::= { wwpLeosCfmExtMEPStatsEntry 6 } 
    
   wwpLeosCfmExtMEPStatsCCMTxmt OBJECT-TYPE
 	SYNTAX Counter64
 	MAX-ACCESS  read-only
     STATUS      current
     DESCRIPTION
             "This object specifies the total CCMs sent."
     ::= { wwpLeosCfmExtMEPStatsEntry 7 } 
   
   wwpLeosCfmExtMEPStatsValidCCMReceived OBJECT-TYPE
 	SYNTAX Counter64
 	MAX-ACCESS  read-only
     STATUS      current
     DESCRIPTION
             "This object specifies the total valid CCMs received."
     ::= { wwpLeosCfmExtMEPStatsEntry 8 }
   
   wwpLeosCfmExtMEPStatsCCMInSequenceReceived OBJECT-TYPE
   	 SYNTAX Counter64
 	 MAX-ACCESS  read-only
     STATUS      current
     DESCRIPTION
             "This object specifies the total CCMs received in sequence."
     ::= { wwpLeosCfmExtMEPStatsEntry 9 }
    
   wwpLeosCfmExtMEPStatsCCMSequenceErrorsReceived OBJECT-TYPE
   	 SYNTAX Counter64
 	 MAX-ACCESS  read-only
     STATUS      current
     DESCRIPTION
             "This object specifies the total CCMs received not in sequence."
     ::= { wwpLeosCfmExtMEPStatsEntry 10 }
   
   wwpLeosCfmExtMEPStatsMDLevelXconCCMReceived  OBJECT-TYPE
   	  SYNTAX Counter64
 	 MAX-ACCESS  read-only
     STATUS      current
     DESCRIPTION
             "This object specifies the Xcon CCMs received."
     ::= { wwpLeosCfmExtMEPStatsEntry 11 }  
   
   wwpLeosCfmExtMEPStatsMAIDXconCCMReceived  OBJECT-TYPE
   	  SYNTAX Counter64
 	 MAX-ACCESS  read-only
     STATUS      current
     DESCRIPTION
             "This object specifies the MAID Xcon CCMs."
     ::= { wwpLeosCfmExtMEPStatsEntry 12 } 
  
  wwpLeosCfmExtMEPStatsIntervalErrorCCMReceived  OBJECT-TYPE
   	  SYNTAX Counter64
 	 MAX-ACCESS  read-only
     STATUS      current
     DESCRIPTION
             "This object specifies the interval error for the CCM received."
     ::= { wwpLeosCfmExtMEPStatsEntry 13 } 
  
  wwpLeosCfmExtMEPStatsRxInvalidCCM  OBJECT-TYPE
   	  SYNTAX Counter64
 	 MAX-ACCESS  read-only
     STATUS      current
     DESCRIPTION
             "This object specified the invalid CCMs received."
     ::= { wwpLeosCfmExtMEPStatsEntry 14 } 
  
  wwpLeosCfmExtMEPStatsLBMTxmt  OBJECT-TYPE
   	  SYNTAX Counter64
 	 MAX-ACCESS  read-only
     STATUS      current
     DESCRIPTION
             "This object specifies the number of LBMs sent."
     ::= { wwpLeosCfmExtMEPStatsEntry 15 }
  
  wwpLeosCfmExtMEPStatsLBRTxmt OBJECT-TYPE
  	 SYNTAX Counter64
 	 MAX-ACCESS  read-only
     STATUS      current
     DESCRIPTION
             "This object specifies the number of LBRs sent."
     ::= { wwpLeosCfmExtMEPStatsEntry 16 } 
  
  wwpLeosCfmExtMEPStatsInOrderLBRReceived OBJECT-TYPE
  	 SYNTAX Counter64
 	 MAX-ACCESS  read-only
     STATUS      current
     DESCRIPTION
             "This object specifies the number of in order LBRs received."
     ::= { wwpLeosCfmExtMEPStatsEntry 17 } 
   
   wwpLeosCfmExtMEPStatsOutOfOrderLBRReceived OBJECT-TYPE
  	 SYNTAX Counter64
 	 MAX-ACCESS  read-only
     STATUS      current
     DESCRIPTION
             "This object specifies the number of out of order LBRs received."
     ::= { wwpLeosCfmExtMEPStatsEntry 18 }
   
   wwpLeosCfmExtMEPStatsContentMismatchLBRReceived  OBJECT-TYPE
  	 SYNTAX Counter64
 	 MAX-ACCESS  read-only
     STATUS      current
     DESCRIPTION
             "This object specifies the number of content mismatch LBRs received."
     ::= { wwpLeosCfmExtMEPStatsEntry 19 }
   
   wwpLeosCfmExtMEPStatsUnexpectedLBRReceived  OBJECT-TYPE
  	 SYNTAX Counter64
 	 MAX-ACCESS  read-only
     STATUS      current
     DESCRIPTION
             "This object specifies the number of unexpected LBRs received."
     ::= { wwpLeosCfmExtMEPStatsEntry 20 }
     
   wwpLeosCfmExtMEPStatsInvalidLBRReceived OBJECT-TYPE
  	 SYNTAX Counter64
 	 MAX-ACCESS  read-only
     STATUS      current
     DESCRIPTION
             "This object specifies the number of invalid LBRs received."
     ::= { wwpLeosCfmExtMEPStatsEntry 21 } 
   
   wwpLeosCfmExtMEPStatsLTMTxmt   OBJECT-TYPE
   	  SYNTAX Counter64
 	 MAX-ACCESS  read-only
     STATUS      current
     DESCRIPTION
             "This object specifies the number of LTMs sent."
     ::= { wwpLeosCfmExtMEPStatsEntry 22 }
   
   wwpLeosCfmExtMEPStatsValidLTMReceived  OBJECT-TYPE
   	  SYNTAX Counter64
 	 MAX-ACCESS  read-only
     STATUS      current
     DESCRIPTION
             "This object specifies the total valid LTMs received."
     ::= { wwpLeosCfmExtMEPStatsEntry 23 } 
   
   wwpLeosCfmExtMEPStatsTotalInvalidLTMReceived OBJECT-TYPE
   	  SYNTAX Counter64
 	  MAX-ACCESS  read-only
      STATUS      current
      DESCRIPTION
             "This object specifies the total invalid LTMs received."
     ::= { wwpLeosCfmExtMEPStatsEntry 24 }
   
   wwpLeosCfmExtMEPStatsInvalidLTRAction  OBJECT-TYPE
   	  SYNTAX Counter64
 	  MAX-ACCESS  read-only
      STATUS      current
      DESCRIPTION
             "This object specifies the total invalid LTR actions."
     ::= { wwpLeosCfmExtMEPStatsEntry 25 }
   
   wwpLeosCfmExtMEPStatsLTRTxmt OBJECT-TYPE
   	  SYNTAX Counter64
 	  MAX-ACCESS  read-only
      STATUS      current
      DESCRIPTION
             "This object specifies the total LTRs sent."
     ::= { wwpLeosCfmExtMEPStatsEntry 26 }  
   
  wwpLeosCfmExtMEPStatsLTRReceived  OBJECT-TYPE
   	  SYNTAX Counter64
 	  MAX-ACCESS  read-only
      STATUS      current
      DESCRIPTION
             "This object specifies the total unexpected LTRs sent."
     ::= { wwpLeosCfmExtMEPStatsEntry 27 } 
   
  wwpLeosCfmExtMEPStatsDMMTxmt  OBJECT-TYPE
   	  SYNTAX Counter64
 	  MAX-ACCESS  read-only
      STATUS      current
      DESCRIPTION
             "This object specifies the total DMMs sent."
     ::= { wwpLeosCfmExtMEPStatsEntry 28 }
   
  wwpLeosCfmExtMEPStatsDMMReceived  OBJECT-TYPE
   	  SYNTAX Counter64
 	  MAX-ACCESS  read-only
      STATUS      current
      DESCRIPTION
             "This object specifies the total DMMs received."
     ::= { wwpLeosCfmExtMEPStatsEntry 29 }
  
  wwpLeosCfmExtMEPStatsDMRTxmt   OBJECT-TYPE
  	  SYNTAX Counter64
 	  MAX-ACCESS  read-only
      STATUS      current
      DESCRIPTION
             "This object specifies the total DMRs sent."
     ::= { wwpLeosCfmExtMEPStatsEntry 30 }
  
  wwpLeosCfmExtMEPStatsDMRReceived  OBJECT-TYPE
  	  SYNTAX Counter64
 	  MAX-ACCESS  read-only
      STATUS      current
      DESCRIPTION
             "This object specifies the total DMRs received."
     ::= { wwpLeosCfmExtMEPStatsEntry 31 } 
  
  wwpLeosCfmExtMEPStatsDMReplyTimeout OBJECT-TYPE
  	  SYNTAX Counter64
 	  MAX-ACCESS  read-only
      STATUS      current
      DESCRIPTION
             "This object specifies the DMR timeout."
     ::= { wwpLeosCfmExtMEPStatsEntry 32 }
  
  wwpLeosCfmExtMEPStatsLMMTxmt OBJECT-TYPE
  	  SYNTAX Counter64
 	  MAX-ACCESS  read-only
      STATUS      current
      DESCRIPTION
             "This object specifies the total LMMs sent. "
     ::= { wwpLeosCfmExtMEPStatsEntry 33 }
  
  wwpLeosCfmExtMEPStatsLMMReceived  OBJECT-TYPE
  	  SYNTAX Counter64
 	  MAX-ACCESS  read-only
      STATUS      current
      DESCRIPTION
             "This object specifies the total LMMs received "
     ::= { wwpLeosCfmExtMEPStatsEntry 34 }
  
  wwpLeosCfmExtMEPStatsLMRTxmt OBJECT-TYPE
  	  SYNTAX Counter64
 	  MAX-ACCESS  read-only
      STATUS      current
      DESCRIPTION
             "This object specifies the total LMRs sent."
     ::= { wwpLeosCfmExtMEPStatsEntry 35 }
 
 wwpLeosCfmExtMEPStatsLMRReceived  OBJECT-TYPE
  	  SYNTAX Counter64
 	  MAX-ACCESS  read-only
      STATUS      current
      DESCRIPTION
             "This object specifies the total LMRs received."
     ::= { wwpLeosCfmExtMEPStatsEntry 36 } 
 
 wwpLeosCfmExtMEPStatsLMRTimeout OBJECT-TYPE
  	  SYNTAX Counter64
 	  MAX-ACCESS  read-only
      STATUS      current
      DESCRIPTION
             "This object specifies the LMR timeout. "
     ::= { wwpLeosCfmExtMEPStatsEntry 37 }  
 
 wwpLeosCfmExtMEPStatsMepIdErrorCCMReceived  OBJECT-TYPE
  	  SYNTAX Counter64
 	  MAX-ACCESS  read-only
      STATUS      current
      DESCRIPTION
             "This object specifies total MEPID Error CCM received. "
     ::= { wwpLeosCfmExtMEPStatsEntry 38 }                        
 
  
 wwpLeosCfmExtMEPStatsClear OBJECT-TYPE
 	SYNTAX INTEGER {
 			clear(1),
 			none(2)
 		}
 	MAX-ACCESS read-write
 	STATUS current
 	DESCRIPTION "Setting this object to clear(1) clears MEP statistics for the given service and MepId.
 		     This object cannot be set to none."
 	::= { wwpLeosCfmExtMEPStatsEntry 40 }    
 	
 wwpLeosCfmExtMEPStatsValidLBMReceived  OBJECT-TYPE
  	  SYNTAX Counter64
 	  MAX-ACCESS  read-only
      STATUS      current
      DESCRIPTION
             "This object specifies the total valid LBMs received."
     ::= { wwpLeosCfmExtMEPStatsEntry 41 }    
 
 wwpLeosCfmExtMEPStatsInvalidLBMReceived  OBJECT-TYPE
  	  SYNTAX Counter64
 	  MAX-ACCESS  read-only
      STATUS      current
      DESCRIPTION
             "This object specifies the total invalid LBMs received."
     ::= { wwpLeosCfmExtMEPStatsEntry 42 }
 
 wwpLeosCfmExtMEPStatsUnexpectedLTRReceived  OBJECT-TYPE
  	  SYNTAX Counter64
 	  MAX-ACCESS  read-only
      STATUS      current
      DESCRIPTION
             "This object specifies the total unexpected LTRs received."
     ::= { wwpLeosCfmExtMEPStatsEntry 43 }
 
 wwpLeosCfmExtMEPStatsInvalidDMMReceived OBJECT-TYPE
  	  SYNTAX Counter64
 	  MAX-ACCESS  read-only
      STATUS      current
      DESCRIPTION
             "This object specifies the total invalid DMMs received."
     ::= { wwpLeosCfmExtMEPStatsEntry 44 }
 
 wwpLeosCfmExtMEPStatsInvalidDMRReceived OBJECT-TYPE
  	  SYNTAX Counter64
 	  MAX-ACCESS  read-only
      STATUS      current
      DESCRIPTION
             "This object specifies the total invalid DMRs received."
     ::= { wwpLeosCfmExtMEPStatsEntry 45 }

 wwpLeosCfmExtMEPStatsUnexpectedDMRReceived OBJECT-TYPE
  	  SYNTAX Counter64
 	  MAX-ACCESS  read-only
      STATUS      current
      DESCRIPTION
             "This object specifies the total unexpected DMRs received."
     ::= { wwpLeosCfmExtMEPStatsEntry 46 }

 wwpLeosCfmExtMEPStatsInvalidLMMReceived OBJECT-TYPE
  	  SYNTAX Counter64
 	  MAX-ACCESS  read-only
      STATUS      current
      DESCRIPTION
             "This object specifies the total invalid LMMs received. "
     ::= { wwpLeosCfmExtMEPStatsEntry 47 }

 wwpLeosCfmExtMEPStatsInvalidLMRReceived OBJECT-TYPE
  	  SYNTAX Counter64
 	  MAX-ACCESS  read-only
      STATUS      current
      DESCRIPTION
             "This object specifies the total invalid LMRs received. "
     ::= { wwpLeosCfmExtMEPStatsEntry 48 }
 
 wwpLeosCfmExtMEPStatsInvalidBlockedOppositeMep OBJECT-TYPE
  	  SYNTAX Counter64
 	  MAX-ACCESS  read-only
      STATUS      current
      DESCRIPTION
             "This object specifies the total invalid frames blocked by opposite MEP."
     ::= { wwpLeosCfmExtMEPStatsEntry 49 }
     
 wwpLeosCfmExtMEPStatsSLMTxmt OBJECT-TYPE
  	  SYNTAX Counter64
 	  MAX-ACCESS  read-only
      STATUS      current
      DESCRIPTION
             "This object specifies the total SLMs sent."
     ::= { wwpLeosCfmExtMEPStatsEntry 50 }
  
  wwpLeosCfmExtMEPStatsSLMReceived  OBJECT-TYPE
  	  SYNTAX Counter64
 	  MAX-ACCESS  read-only
      STATUS      current
      DESCRIPTION
             "This object specifies the total SLMs received."
     ::= { wwpLeosCfmExtMEPStatsEntry 51 }
  
  wwpLeosCfmExtMEPStatsSLRTxmt OBJECT-TYPE
  	  SYNTAX Counter64
 	  MAX-ACCESS  read-only
      STATUS      current
      DESCRIPTION
             "This object specifies the total SLRs sent."
     ::= { wwpLeosCfmExtMEPStatsEntry 52 }
 
 wwpLeosCfmExtMEPStatsSLRReceived  OBJECT-TYPE
  	  SYNTAX Counter64
 	  MAX-ACCESS  read-only
      STATUS      current
      DESCRIPTION
             "This object specifies the total SLRs received."
     ::= { wwpLeosCfmExtMEPStatsEntry 53 } 
 
 wwpLeosCfmExtMEPStatsSLRTimeout OBJECT-TYPE
  	  SYNTAX Counter64
 	  MAX-ACCESS  read-only
      STATUS      current
      DESCRIPTION
             "This object specifies the SLR timeout."
     ::= { wwpLeosCfmExtMEPStatsEntry 54 }   
     
  wwpLeosCfmExtMEPStatsInvalidSLMReceived OBJECT-TYPE
       SYNTAX Counter64
       MAX-ACCESS read-only
       STATUS current
       DESCRIPTION
              "This object specifies invalid SLMs received by this MEP."
       ::= { wwpLeosCfmExtMEPStatsEntry 55 }
       
  wwpLeosCfmExtMEPStatsInvalidSLRReceived OBJECT-TYPE
       SYNTAX Counter64
       MAX-ACCESS read-only
       STATUS current
       DESCRIPTION
              "This object specifies invalid SLRs received by this MEP."
       ::= { wwpLeosCfmExtMEPStatsEntry 56 }
 
  wwpLeosCfmExtMEPStatsTotalCSFTxmt OBJECT-TYPE
       SYNTAX Counter64
       MAX-ACCESS read-only
       STATUS current
       DESCRIPTION
              "This object specifies total CSFs transmitted by this MEP."
       ::= { wwpLeosCfmExtMEPStatsEntry 57 }
 
  wwpLeosCfmExtMEPStatsCSFLosTxmt OBJECT-TYPE
       SYNTAX Counter64
       MAX-ACCESS read-only
       STATUS current
       DESCRIPTION
              "This object specifies CSF Los frames transmitted by this MEP."
       ::= { wwpLeosCfmExtMEPStatsEntry 58 }

  wwpLeosCfmExtMEPStatsCSFDciTxmt OBJECT-TYPE
       SYNTAX Counter64
       MAX-ACCESS read-only
       STATUS current
       DESCRIPTION
              "This object specifies CSF Dci frames transmitted by this MEP."
       ::= { wwpLeosCfmExtMEPStatsEntry 59 }

  wwpLeosCfmExtMEPStatsValidCSFReceived OBJECT-TYPE
       SYNTAX Counter64
       MAX-ACCESS read-only
       STATUS current
       DESCRIPTION
              "This object specifies total valid CSFs received by this MEP."
       ::= { wwpLeosCfmExtMEPStatsEntry 60 }

  wwpLeosCfmExtMEPStatsCSFLosReceived OBJECT-TYPE
       SYNTAX Counter64
       MAX-ACCESS read-only
       STATUS current
       DESCRIPTION
              "This object specifies valid CSF Los frame received by this MEP."
       ::= { wwpLeosCfmExtMEPStatsEntry 61 }

  wwpLeosCfmExtMEPStatsCSFDciReceived OBJECT-TYPE
       SYNTAX Counter64
       MAX-ACCESS read-only
       STATUS current
       DESCRIPTION
              "This object specifies valid CSF Dci frame received by this MEP."
       ::= { wwpLeosCfmExtMEPStatsEntry 62 }

  wwpLeosCfmExtMEPStatsInvalidCSFReceived OBJECT-TYPE
       SYNTAX Counter64
       MAX-ACCESS read-only
       STATUS current
       DESCRIPTION
              "This object specifies total invalid CSFs received by this MEP."
       ::= { wwpLeosCfmExtMEPStatsEntry 63 }

 --
 -- Last Statistics Table
 --
 
 wwpLeosCfmExtMEPLastStatsTable OBJECT-TYPE
     SYNTAX     SEQUENCE OF WwpLeosCfmExtMEPLastStatsEntry
     MAX-ACCESS not-accessible
     STATUS     current
     DESCRIPTION
            "The (conceptual) table listing the configuration
            parameters for the CFM MEP table."  
     ::= { wwpLeosCfmExtMEP 3 }
                
 wwpLeosCfmExtMEPLastStatsEntry OBJECT-TYPE
     SYNTAX      WwpLeosCfmExtMEPLastStatsEntry
     MAX-ACCESS  not-accessible
     STATUS      current
     DESCRIPTION
           "An entry (conceptual row) in the wwpLeosCfmMEPTable."
     --   wwpLeosCfmExtMEPId is the new index in place of mepport
     INDEX {wwpLeosCfmServiceIndex, wwpLeosCfmExtMEPId}
     ::= { wwpLeosCfmExtMEPLastStatsTable 1 }   

  
 WwpLeosCfmExtMEPLastStatsEntry ::= SEQUENCE {                    
 		wwpLeosCfmExtMEPLastStatsPriority				Counter64,			
 		wwpLeosCfmExtMEPLastStatsLBMCount				Counter64,
 		wwpLeosCfmExtMEPLastStatsLBMSent				Counter64,
 		wwpLeosCfmExtMEPLastStatsLBMToSend				Counter64,
 		wwpLeosCfmExtMEPLastStatsInOrderLBRReceived		Counter64,
 		wwpLeosCfmExtMEPLastStatsOutOfOrderLBRReceived  Counter64,
 		wwpLeosCfmExtMEPLastStatsDMMPriority			Counter64,
 		wwpLeosCfmExtMEPLastStatsDMMTxmt				Counter64,
 		wwpLeosCfmExtMEPLastStatsDMMReceived			Counter64,
 		wwpLeosCfmExtMEPLastStatsDMMDelay				Counter64,
 		wwpLeosCfmExtMEPLastStatsDMMJitter				Counter64,
 		wwpLeosCfmExtMEPLastStatsLMMPriority			Counter64,
 		wwpLeosCfmExtMEPLastStatsLMMTxtm				Counter64,
 		wwpLeosCfmExtMEPLastStatsLMMReceived			Counter64,
 		wwpLeosCfmExtMEPLastStatsFrameLossNear			Counter64,
 		wwpLeosCfmExtMEPLastStatsFrameLossFar			Counter64,
 		wwpLeosCfmExtMEPLastStatsLTMPriority			Counter64,
 		wwpLeosCfmExtMEPLastStatsLTMSequenceNo			Counter64,
 		wwpLeosCfmExtMEPLastStatsLTMInitialTTL			Counter64,
 		wwpLeosCfmExtMEPLastStatsFrameLossBadSequence	Counter64,
 		wwpLeosCfmExtMEPLastStatsDMMMinDelay			Counter64,
 		wwpLeosCfmExtMEPLastStatsDMMMaxDelay			Counter64,
 		wwpLeosCfmExtMEPLastStatsDMMMinJitter			Counter64,
 		wwpLeosCfmExtMEPLastStatsDMMMaxJitter			Counter64,
		wwpLeosCfmExtMEPLastStatsSLMPriority			Counter64,
		wwpLeosCfmExtMEPLastStatsSLMTxmt				Counter64,
		wwpLeosCfmExtMEPLastStatsSLMReceived			Counter64,
		wwpLeosCfmExtMEPLastStatsSLMNearLoss			Counter64,
		wwpLeosCfmExtMEPLastStatsSLMFarLoss				Counter64,
 		wwpLeosCfmExtMEPLastStatsDMMTotalJitter			Counter64,
 		wwpLeosCfmExtMEPLastStatsDMMForwardMinJitter		Counter64,
 		wwpLeosCfmExtMEPLastStatsDMMForwardMaxJitter		Counter64,
 		wwpLeosCfmExtMEPLastStatsDMMForwardAveJitter		Counter64,
 		wwpLeosCfmExtMEPLastStatsDMMForwardTotalJitter		Counter64,
 		wwpLeosCfmExtMEPLastStatsDMMBackwardMinJitter		Counter64,
 		wwpLeosCfmExtMEPLastStatsDMMBackwardMaxJitter		Counter64,
 		wwpLeosCfmExtMEPLastStatsDMMBackwardAveJitter		Counter64,
 		wwpLeosCfmExtMEPLastStatsDMMBackwardTotalJitter		Counter64,
 		wwpLeosCfmExtMEPLastStatsDMMSuspect   			TruthValue,
 		wwpLeosCfmExtMEPLastStatsDMMForwardMinDelay   		Integer32,
		wwpLeosCfmExtMEPLastStatsDMMForwardAveDelay   		Integer32,
		wwpLeosCfmExtMEPLastStatsDMMForwardMaxDelay	    	Integer32,
 		wwpLeosCfmExtMEPLastStatsDMMBackwardMinDelay		Integer32,
 		wwpLeosCfmExtMEPLastStatsDMMBackwardAveDelay		Integer32,
  		wwpLeosCfmExtMEPLastStatsDMMBackwardMaxDelay		Integer32
 } 			
 wwpLeosCfmExtMEPLastStatsPriority	OBJECT-TYPE
 	SYNTAX Counter64
 	MAX-ACCESS read-only
 	STATUS current
 	DESCRIPTION
 		"This object specifies the last LBM priority."
 	::= {wwpLeosCfmExtMEPLastStatsEntry 1}
 
 wwpLeosCfmExtMEPLastStatsLBMCount OBJECT-TYPE
 	SYNTAX Counter64
 	MAX-ACCESS read-only
 	STATUS current
 	DESCRIPTION
 		"This object specifies the last LBM count."
 	::= {wwpLeosCfmExtMEPLastStatsEntry 2} 
 wwpLeosCfmExtMEPLastStatsLBMSent  OBJECT-TYPE
 	SYNTAX Counter64
 	MAX-ACCESS read-only
 	STATUS current
 	DESCRIPTION
 		"This object specifies the last number LBM sent."
 	::= {wwpLeosCfmExtMEPLastStatsEntry 3} 
 
 wwpLeosCfmExtMEPLastStatsLBMToSend OBJECT-TYPE
 	SYNTAX Counter64
 	MAX-ACCESS read-only
 	STATUS current
 	DESCRIPTION
 		"This object specifies the last LBM to send."
 	::= {wwpLeosCfmExtMEPLastStatsEntry 4}		
 
 wwpLeosCfmExtMEPLastStatsInOrderLBRReceived OBJECT-TYPE
 	SYNTAX Counter64
 	MAX-ACCESS read-only
 	STATUS current
 	DESCRIPTION
 		"This object specifies the last in order LBR received."
 	::= {wwpLeosCfmExtMEPLastStatsEntry 5}			
 
 wwpLeosCfmExtMEPLastStatsOutOfOrderLBRReceived	OBJECT-TYPE
 	SYNTAX Counter64
 	MAX-ACCESS read-only
 	STATUS current
 	DESCRIPTION
 		"This object specifies the last out of order LBR received."
 	::= {wwpLeosCfmExtMEPLastStatsEntry 6}			
 			
 wwpLeosCfmExtMEPLastStatsDMMPriority OBJECT-TYPE
 	SYNTAX Counter64
 	MAX-ACCESS read-only
 	STATUS current
 	DESCRIPTION
 		"This object specifies the last DMM priority"
 	::= {wwpLeosCfmExtMEPLastStatsEntry 7}
 
 wwpLeosCfmExtMEPLastStatsDMMTxmt  OBJECT-TYPE
 	SYNTAX Counter64
 	MAX-ACCESS read-only
 	STATUS current
 	DESCRIPTION
 		"This object specifies the number of last DMM sent."
 	::= {wwpLeosCfmExtMEPLastStatsEntry 8} 
 
 wwpLeosCfmExtMEPLastStatsDMMReceived  OBJECT-TYPE
 	SYNTAX Counter64
 	MAX-ACCESS read-only
 	STATUS current
 	DESCRIPTION
 		"This object specifies the last DMM received."
 	::= {wwpLeosCfmExtMEPLastStatsEntry 9} 
 
 wwpLeosCfmExtMEPLastStatsDMMDelay  OBJECT-TYPE
 	SYNTAX Counter64
 	MAX-ACCESS read-only
 	STATUS current
 	DESCRIPTION
 		"This object specifies last DMM delay."
 	::= {wwpLeosCfmExtMEPLastStatsEntry 10} 
 
 wwpLeosCfmExtMEPLastStatsDMMJitter  OBJECT-TYPE
 	SYNTAX Counter64
 	MAX-ACCESS read-only
 	STATUS current
 	DESCRIPTION
 		"This object specifies the last DMM jitter."
 	::= {wwpLeosCfmExtMEPLastStatsEntry 11} 
 
 wwpLeosCfmExtMEPLastStatsLMMPriority  OBJECT-TYPE
 	SYNTAX Counter64
 	MAX-ACCESS read-only
 	STATUS current
 	DESCRIPTION
 		"This object specifies the last LMM priority."
 	::= {wwpLeosCfmExtMEPLastStatsEntry 12}
 	
 wwpLeosCfmExtMEPLastStatsLMMTxtm OBJECT-TYPE
 	SYNTAX Counter64
 	MAX-ACCESS read-only
 	STATUS current
 	DESCRIPTION
 		"This object specifies last LMM sent."
 	::= {wwpLeosCfmExtMEPLastStatsEntry 13}

 wwpLeosCfmExtMEPLastStatsLMMReceived  OBJECT-TYPE
 	SYNTAX Counter64
 	MAX-ACCESS read-only
 	STATUS current
 	DESCRIPTION
 		"This object specifies the number of last LMM received."
 	::= {wwpLeosCfmExtMEPLastStatsEntry 14}
 
 wwpLeosCfmExtMEPLastStatsFrameLossNear OBJECT-TYPE
 	SYNTAX Counter64
 	MAX-ACCESS read-only
 	STATUS current
 	DESCRIPTION
 		"This object specifies the last near frames loss."
 	::= {wwpLeosCfmExtMEPLastStatsEntry 15}	
 
 wwpLeosCfmExtMEPLastStatsFrameLossFar 	OBJECT-TYPE
 	SYNTAX Counter64
 	MAX-ACCESS read-only
 	STATUS current
 	DESCRIPTION
 		"This object specifies the last far frames loss."
 	::= {wwpLeosCfmExtMEPLastStatsEntry 16}	
 
 wwpLeosCfmExtMEPLastStatsLTMPriority OBJECT-TYPE
 	SYNTAX Counter64
 	MAX-ACCESS read-only
 	STATUS current
 	DESCRIPTION
 		"This object specifies the last LTM priority."
 	::= {wwpLeosCfmExtMEPLastStatsEntry 17}
 
 wwpLeosCfmExtMEPLastStatsLTMSequenceNo OBJECT-TYPE
 	SYNTAX Counter64
 	MAX-ACCESS read-only
 	STATUS current
 	DESCRIPTION
 		"This object specifies the last LTM sequence number."
 	::= {wwpLeosCfmExtMEPLastStatsEntry 18}   
 
 wwpLeosCfmExtMEPLastStatsLTMInitialTTL  OBJECT-TYPE
 	SYNTAX Counter64
 	MAX-ACCESS read-only
 	STATUS current
 	DESCRIPTION
 		"This object specifies the last initial TTL LTM."
 	::= {wwpLeosCfmExtMEPLastStatsEntry 19}    

 wwpLeosCfmExtMEPLastStatsFrameLossBadSequence OBJECT-TYPE
 	SYNTAX Counter64
 	MAX-ACCESS read-only
 	STATUS current
 	DESCRIPTION
 		"This object specifes the number of frames with bad sequence numbers measured
 		during the last LMM performance test on the given service and Mep."
 	::= {wwpLeosCfmExtMEPLastStatsEntry 20}
 
 wwpLeosCfmExtMEPLastStatsDMMMinDelay  OBJECT-TYPE
 	SYNTAX Counter64
 	MAX-ACCESS read-only
 	STATUS current
 	DESCRIPTION
 		"This object specifies the last DMM minimum delay."
 	::= {wwpLeosCfmExtMEPLastStatsEntry 21} 
 
 wwpLeosCfmExtMEPLastStatsDMMMaxDelay  OBJECT-TYPE
 	SYNTAX Counter64
 	MAX-ACCESS read-only
 	STATUS current
 	DESCRIPTION
 		"This object specifies the last DMM maximum delay."
 	::= {wwpLeosCfmExtMEPLastStatsEntry 22} 
 
 wwpLeosCfmExtMEPLastStatsDMMMinJitter  OBJECT-TYPE
 	SYNTAX Counter64
 	MAX-ACCESS read-only
 	STATUS current
 	DESCRIPTION
 		"This object specifies the last DMM minimum jitter."
 	::= {wwpLeosCfmExtMEPLastStatsEntry 23} 
 
 wwpLeosCfmExtMEPLastStatsDMMMaxJitter  OBJECT-TYPE
 	SYNTAX Counter64
 	MAX-ACCESS read-only
 	STATUS current
 	DESCRIPTION
 		"This object specifies the last DMM maximum jitter."
 	::= {wwpLeosCfmExtMEPLastStatsEntry 24} 

 wwpLeosCfmExtMEPLastStatsSLMPriority  OBJECT-TYPE
        SYNTAX Counter64
        MAX-ACCESS read-only
        STATUS current
        DESCRIPTION
                "This object specifies the last SLM session priority."
        ::= {wwpLeosCfmExtMEPLastStatsEntry 25}

 wwpLeosCfmExtMEPLastStatsSLMTxmt      OBJECT-TYPE
        SYNTAX Counter64
        MAX-ACCESS read-only
        STATUS current
        DESCRIPTION
                "This object specifies the number of SLM frames last transmitted."
        ::= {wwpLeosCfmExtMEPLastStatsEntry 26}

 wwpLeosCfmExtMEPLastStatsSLMReceived  OBJECT-TYPE
        SYNTAX Counter64
        MAX-ACCESS read-only
        STATUS current
        DESCRIPTION
                "This object specifies the number of SLM frames last received."
        ::= {wwpLeosCfmExtMEPLastStatsEntry 27}

 wwpLeosCfmExtMEPLastStatsSLMNearLoss  OBJECT-TYPE
        SYNTAX Counter64
        MAX-ACCESS read-only
        STATUS current
        DESCRIPTION
                "This object specifies the Near Loss in the last SLM session."
        ::= {wwpLeosCfmExtMEPLastStatsEntry 28}

 wwpLeosCfmExtMEPLastStatsSLMFarLoss   OBJECT-TYPE
        SYNTAX Counter64
        MAX-ACCESS read-only
        STATUS current
        DESCRIPTION
                "This object specifies the Far Loss in the last SLM session."
        ::= {wwpLeosCfmExtMEPLastStatsEntry 29}

 wwpLeosCfmExtMEPLastStatsDMMTotalJitter  OBJECT-TYPE
        SYNTAX Counter64
        MAX-ACCESS read-only
        STATUS current
        DESCRIPTION
                "This object specifies the last total DMM jitter."
        ::= {wwpLeosCfmExtMEPLastStatsEntry 30} 

 wwpLeosCfmExtMEPLastStatsDMMForwardMinJitter  OBJECT-TYPE
        SYNTAX Counter64
        MAX-ACCESS read-only
        STATUS current
        DESCRIPTION
                "This object specifies the last DMM minimum jitter in forward direction."
        ::= {wwpLeosCfmExtMEPLastStatsEntry 31} 

 wwpLeosCfmExtMEPLastStatsDMMForwardMaxJitter  OBJECT-TYPE
        SYNTAX Counter64
        MAX-ACCESS read-only
        STATUS current
        DESCRIPTION
                "This object specifies the last DMM maximum jitter in forward direction."
        ::= {wwpLeosCfmExtMEPLastStatsEntry 32} 

 wwpLeosCfmExtMEPLastStatsDMMForwardAveJitter  OBJECT-TYPE
        SYNTAX Counter64
        MAX-ACCESS read-only
        STATUS current
        DESCRIPTION
                "This object specifies the last DMM average jitter in forward direction."
        ::= {wwpLeosCfmExtMEPLastStatsEntry 33} 

 wwpLeosCfmExtMEPLastStatsDMMForwardTotalJitter  OBJECT-TYPE
        SYNTAX Counter64
        MAX-ACCESS read-only
        STATUS current
        DESCRIPTION
                "This object specifies the last DMM total jitter in forward direction."
        ::= {wwpLeosCfmExtMEPLastStatsEntry 34} 

 wwpLeosCfmExtMEPLastStatsDMMBackwardMinJitter  OBJECT-TYPE
        SYNTAX Counter64
        MAX-ACCESS read-only
        STATUS current
        DESCRIPTION
                "This object specifies the last DMM minimum jitter in backward direction."
        ::= {wwpLeosCfmExtMEPLastStatsEntry 35} 

 wwpLeosCfmExtMEPLastStatsDMMBackwardMaxJitter  OBJECT-TYPE
        SYNTAX Counter64
        MAX-ACCESS read-only
        STATUS current
        DESCRIPTION
                "This object specifies the last DMM maximum jitter in backward direction."
        ::= {wwpLeosCfmExtMEPLastStatsEntry 36} 

 wwpLeosCfmExtMEPLastStatsDMMBackwardAveJitter  OBJECT-TYPE
        SYNTAX Counter64
        MAX-ACCESS read-only
        STATUS current
        DESCRIPTION
                "This object specifies the last DMM average jitter in backward direction."
        ::= {wwpLeosCfmExtMEPLastStatsEntry 37} 

 wwpLeosCfmExtMEPLastStatsDMMBackwardTotalJitter  OBJECT-TYPE
        SYNTAX Counter64
        MAX-ACCESS read-only
        STATUS current
        DESCRIPTION
                "This object specifies the last DMM total jitter in backward direction."
        ::= {wwpLeosCfmExtMEPLastStatsEntry 38} 

 wwpLeosCfmExtMEPLastStatsDMMSuspect  OBJECT-TYPE
        SYNTAX TruthValue
        MAX-ACCESS read-only
        STATUS current
        DESCRIPTION
                "This object indicates that there was discontinuity in DMM Performance Measurement.
                 Condition for discontinuity include:
                 a) The conducting of performance measurement is halted before the current measurement interval is completed."
        ::= {wwpLeosCfmExtMEPLastStatsEntry 39} 

 wwpLeosCfmExtMEPLastStatsDMMForwardMinDelay  OBJECT-TYPE
        SYNTAX Integer32
        MAX-ACCESS read-only
        STATUS current
        DESCRIPTION
                "This object specifies the last DMM minimum delay in forward direction."
        ::= {wwpLeosCfmExtMEPLastStatsEntry 40} 

 wwpLeosCfmExtMEPLastStatsDMMForwardAveDelay  OBJECT-TYPE
        SYNTAX Integer32
        MAX-ACCESS read-only
        STATUS current
        DESCRIPTION
                "This object specifies the last DMM average delay in forward direction."
        ::= {wwpLeosCfmExtMEPLastStatsEntry 41} 

 wwpLeosCfmExtMEPLastStatsDMMForwardMaxDelay  OBJECT-TYPE
        SYNTAX Integer32
        MAX-ACCESS read-only
        STATUS current
        DESCRIPTION
                "This object specifies the last DMM maximum delay in forward direction."
        ::= {wwpLeosCfmExtMEPLastStatsEntry 42} 

 wwpLeosCfmExtMEPLastStatsDMMBackwardMinDelay  OBJECT-TYPE
        SYNTAX Integer32
        MAX-ACCESS read-only
        STATUS current
        DESCRIPTION
                "This object specifies the last DMM minimum delay in backward direction."
        ::= {wwpLeosCfmExtMEPLastStatsEntry 43} 

 wwpLeosCfmExtMEPLastStatsDMMBackwardAveDelay  OBJECT-TYPE
        SYNTAX Integer32
        MAX-ACCESS read-only
        STATUS current
        DESCRIPTION
                "This object specifies the last DMM average delay in backward direction."
        ::= {wwpLeosCfmExtMEPLastStatsEntry 44} 

 wwpLeosCfmExtMEPLastStatsDMMBackwardMaxDelay  OBJECT-TYPE
        SYNTAX Integer32
        MAX-ACCESS read-only
        STATUS current
        DESCRIPTION
                "This object specifies the last DMM maximum delay in backward direction."
        ::= {wwpLeosCfmExtMEPLastStatsEntry 45} 
 		
 wwpLeosCfmExtMEPClearStatistics OBJECT-TYPE
 	SYNTAX INTEGER {
 		clear(1),
 		none(2)
 		}
 	MAX-ACCESS read-write
 	STATUS current
 	DESCRIPTION 
	     "Setting this object to clear(1), clears statistics for all Meps across all services,"
 	DEFVAL {none}
 	::= {wwpLeosCfmExtMEP 4}


--
-- CFM MEP Delay History
--
   
 wwpLeosCfmExtMEPDelayHistoryTable OBJECT-TYPE
     SYNTAX     	SEQUENCE OF WwpLeosCfmExtMEPDelayHistoryEntry
     MAX-ACCESS 	not-accessible
     STATUS     	current
     DESCRIPTION 	"The (conceptual) table listing the Y.1731 Delay
     				History table for the CFM MEP."  
     ::= { wwpLeosCfmExtMEP 5 }
                
 wwpLeosCfmExtMEPDelayHistoryEntry OBJECT-TYPE
     SYNTAX      	WwpLeosCfmExtMEPDelayHistoryEntry
     MAX-ACCESS  	not-accessible
     STATUS      	current
     DESCRIPTION    "An entry (conceptual row) in the wwpLeosCfmMEPDelayHistoryTable."
     INDEX {wwpLeosCfmServiceIndex, wwpLeosCfmExtMEPId, wwpLeosCfmExtMEPDelayHistoryIndex}
     ::= { wwpLeosCfmExtMEPDelayHistoryTable 1 }   
 
  WwpLeosCfmExtMEPDelayHistoryEntry ::=  SEQUENCE {
     wwpLeosCfmExtMEPDelayHistoryIndex					INTEGER,
  	 wwpLeosCfmExtMEPDelayHistoryStatus					INTEGER,
  	 wwpLeosCfmExtMEPDelayHistoryInterval				INTEGER,
  	 wwpLeosCfmExtMEPDelayHistoryPriority				INTEGER,
  	 wwpLeosCfmExtMEPDelayHistoryMEPId					Unsigned32,
  	 wwpLeosCfmExtMEPDelayHistoryNumDMMSent				Unsigned32,
  	 wwpLeosCfmExtMEPDelayHistoryNumDMRReceived			Unsigned32,
  	 wwpLeosCfmExtMEPDelayHistoryMinDelay				Unsigned32,
  	 wwpLeosCfmExtMEPDelayHistoryAveDelay				Unsigned32,
  	 wwpLeosCfmExtMEPDelayHistoryMaxDelay				Unsigned32, 
  	 wwpLeosCfmExtMEPDelayHistoryMinJitter				Unsigned32,
  	 wwpLeosCfmExtMEPDelayHistoryAveJitter				Unsigned32,
  	 wwpLeosCfmExtMEPDelayHistoryMaxJitter				Unsigned32, 
 	 wwpLeosCfmExtMEPDelayHistoryStartTime				Unsigned32,
 	 wwpLeosCfmExtMEPDelayHistoryStopTime				Unsigned32,
  	 wwpLeosCfmExtMEPDelayHistoryClear				INTEGER,
  	 wwpLeosCfmExtMEPDelayHistoryTotalJitter			Counter64, 
  	 wwpLeosCfmExtMEPDelayHistoryForwardMinJitter		Unsigned32,
  	 wwpLeosCfmExtMEPDelayHistoryForwardAveJitter		Unsigned32,
  	 wwpLeosCfmExtMEPDelayHistoryForwardMaxJitter		Unsigned32, 
  	 wwpLeosCfmExtMEPDelayHistoryForwardTotalJitter		Counter64, 
  	 wwpLeosCfmExtMEPDelayHistoryBackwardMinJitter		Unsigned32,
  	 wwpLeosCfmExtMEPDelayHistoryBackwardAveJitter		Unsigned32,
  	 wwpLeosCfmExtMEPDelayHistoryBackwardMaxJitter		Unsigned32, 
  	 wwpLeosCfmExtMEPDelayHistoryBackwardTotalJitter	Counter64, 
  	 wwpLeosCfmExtMEPDelayHistorySuspect				TruthValue,
  	 wwpLeosCfmExtMEPDelayHistoryForwardMinDelay		Integer32,
  	 wwpLeosCfmExtMEPDelayHistoryForwardAveDelay		Integer32,
  	 wwpLeosCfmExtMEPDelayHistoryForwardMaxDelay		Integer32,
  	 wwpLeosCfmExtMEPDelayHistoryBackwardMinDelay		Integer32,
  	 wwpLeosCfmExtMEPDelayHistoryBackwardAveDelay		Integer32,
  	 wwpLeosCfmExtMEPDelayHistoryBackwardMaxDelay		Integer32
  }

 wwpLeosCfmExtMEPDelayHistoryIndex OBJECT-TYPE
    SYNTAX      	INTEGER (0..255)
    MAX-ACCESS  	not-accessible
    STATUS      	current
    DESCRIPTION		"This is the history entry index into the table."
    ::= { wwpLeosCfmExtMEPDelayHistoryEntry 1 }
 	
 wwpLeosCfmExtMEPDelayHistoryStatus OBJECT-TYPE
    SYNTAX      	INTEGER {
     							running(1),
     							done(2),
     							canceled(3),
     							timeout(4)
     						}
    MAX-ACCESS  	read-only
    STATUS      	current
    DESCRIPTION     "This object specifies the status of the test sent on the given service and MEP."  
    ::= { wwpLeosCfmExtMEPDelayHistoryEntry 2 } 
 
 wwpLeosCfmExtMEPDelayHistoryInterval OBJECT-TYPE
    SYNTAX      	INTEGER (0..7)
    MAX-ACCESS  	read-only
    STATUS      	current
    DESCRIPTION     "This object specifies the transmit rate of the Y.1731 DMM Frames sent on the given service and MEP."  
    ::= { wwpLeosCfmExtMEPDelayHistoryEntry 3 } 
 
 wwpLeosCfmExtMEPDelayHistoryPriority OBJECT-TYPE
    SYNTAX      	INTEGER (0..7)
    MAX-ACCESS  	read-only
    STATUS      	current
    DESCRIPTION     "This object specifies the priority of the Y.1731 DMM Frames sent on the given service and MEP."  
    ::= { wwpLeosCfmExtMEPDelayHistoryEntry 4 } 
 
 wwpLeosCfmExtMEPDelayHistoryMEPId OBJECT-TYPE
    SYNTAX      	Unsigned32 (1..8191)
    MAX-ACCESS  	read-only
    STATUS      	current
    DESCRIPTION     "This object specifies the remote MEP id the test was ran against."
    ::= { wwpLeosCfmExtMEPDelayHistoryEntry 5 }
     
 wwpLeosCfmExtMEPDelayHistoryNumDMMSent OBJECT-TYPE
 	SYNTAX			Unsigned32
 	MAX-ACCESS		read-only
 	STATUS			current 
    DESCRIPTION		"This object specifies the number of DMM frames sent on the given service and MEP."
    ::= { wwpLeosCfmExtMEPDelayHistoryEntry 6 }
    
 wwpLeosCfmExtMEPDelayHistoryNumDMRReceived OBJECT-TYPE
 	SYNTAX			Unsigned32
 	MAX-ACCESS		read-only
 	STATUS			current 
    DESCRIPTION		"This object specifies the number of DMR frames received on the given service and MEP."
    ::= { wwpLeosCfmExtMEPDelayHistoryEntry 7 }
    
 wwpLeosCfmExtMEPDelayHistoryMinDelay OBJECT-TYPE
 	SYNTAX			Unsigned32
 	MAX-ACCESS		read-only
 	STATUS			current 
    DESCRIPTION		"This object specifies the minimum delay(microseconds) seen on DMR frames received on the given service and MEP."
    ::= { wwpLeosCfmExtMEPDelayHistoryEntry 8 }
    
 wwpLeosCfmExtMEPDelayHistoryAveDelay OBJECT-TYPE
 	SYNTAX			Unsigned32
 	MAX-ACCESS		read-only
 	STATUS			current 
    DESCRIPTION		"This object specifies the average delay(microseconds) seen on DMR frames received on the given service and MEP."
    ::= { wwpLeosCfmExtMEPDelayHistoryEntry 9 }
    
 wwpLeosCfmExtMEPDelayHistoryMaxDelay OBJECT-TYPE
 	SYNTAX			Unsigned32
 	MAX-ACCESS		read-only
 	STATUS			current 
    DESCRIPTION		"This object specifies the maximum delay(microseconds) seen on DMR frames received on the given service and MEP."
    ::= { wwpLeosCfmExtMEPDelayHistoryEntry 10 }
    
 wwpLeosCfmExtMEPDelayHistoryMinJitter OBJECT-TYPE
 	SYNTAX			Unsigned32
 	MAX-ACCESS		read-only
 	STATUS			current 
    DESCRIPTION		"This object specifies the minimum jitter(microseconds) seen on DMR frames received on the given service and MEP."
    ::= { wwpLeosCfmExtMEPDelayHistoryEntry 11 }
    
 wwpLeosCfmExtMEPDelayHistoryAveJitter OBJECT-TYPE
 	SYNTAX			Unsigned32
 	MAX-ACCESS		read-only
 	STATUS			current 
    DESCRIPTION		"This object specifies the average jitter(microseconds) seen on DMR frames received on the given service and MEP."
    ::= { wwpLeosCfmExtMEPDelayHistoryEntry 12 }
    
 wwpLeosCfmExtMEPDelayHistoryMaxJitter OBJECT-TYPE
 	SYNTAX			Unsigned32
 	MAX-ACCESS		read-only
 	STATUS			current 
    DESCRIPTION		"This object specifies the maximum jitter(microseconds) seen on DMR frames received on the given service and MEP."
    ::= { wwpLeosCfmExtMEPDelayHistoryEntry 13 }
 
 wwpLeosCfmExtMEPDelayHistoryStartTime OBJECT-TYPE
 	SYNTAX			Unsigned32
 	MAX-ACCESS		read-only
 	STATUS			current
 	DESCRIPTION		"This object specifies the time the test began on the given service and MEP.
 					The timestamp is the number of seconds since 12AM Jan 1st, 1970"
 	::= { wwpLeosCfmExtMEPDelayHistoryEntry 14 }
 
 wwpLeosCfmExtMEPDelayHistoryStopTime OBJECT-TYPE
 	SYNTAX			Unsigned32
 	MAX-ACCESS		read-only
 	STATUS			current
 	DESCRIPTION		
	    "This object specifies the time the test terminated on the given service and MEP.
	    The timestamp is the number of seconds since 12AM Jan 1st, 1970."
 	::= { wwpLeosCfmExtMEPDelayHistoryEntry 15 }
 	
 wwpLeosCfmExtMEPDelayHistoryClear OBJECT-TYPE
 	SYNTAX 			INTEGER {
 								clear(1),
 								none(2)
 							}
 	MAX-ACCESS 		read-write
 	STATUS 			current
 	DESCRIPTION 	
	     "Setting this object to clear(1) clears MEP delay history for the given service and MepId.  
	     This object cannot be set to none."
 	::= { wwpLeosCfmExtMEPDelayHistoryEntry 16 }    
  
 wwpLeosCfmExtMEPDelayHistoryTotalJitter OBJECT-TYPE
 	SYNTAX			Counter64
 	MAX-ACCESS		read-only
 	STATUS			current 
 	DESCRIPTION 	
	     "This object specifies the total jitter(microseconds) seen on DMR frames received 
	      on the given service and MEP."
 	::= { wwpLeosCfmExtMEPDelayHistoryEntry 17 }
    
 wwpLeosCfmExtMEPDelayHistoryForwardMinJitter OBJECT-TYPE
 	SYNTAX			Unsigned32
 	MAX-ACCESS		read-only
 	STATUS			current 
 	DESCRIPTION 	
	     "This object specifies the minimum jitter(microseconds) seen on DMR frames received 
	      on the given service and MEP in forward direction."
 	::= { wwpLeosCfmExtMEPDelayHistoryEntry 18 }
   
 wwpLeosCfmExtMEPDelayHistoryForwardMaxJitter OBJECT-TYPE
 	SYNTAX			Unsigned32
 	MAX-ACCESS		read-only
 	STATUS			current 
 	DESCRIPTION 	
	     "This object specifies the maximum jitter(microseconds) seen on DMR frames received 
	      on the given service and MEP in forward direction."
 	::= { wwpLeosCfmExtMEPDelayHistoryEntry 19 }

 wwpLeosCfmExtMEPDelayHistoryForwardAveJitter OBJECT-TYPE
 	SYNTAX			Unsigned32
 	MAX-ACCESS		read-only
 	STATUS			current 
 	DESCRIPTION 	
	     "This object specifies the average jitter(microseconds) seen on DMR frames received 
	      on the given service and MEP in forward direction."
 	::= { wwpLeosCfmExtMEPDelayHistoryEntry 20 }

 wwpLeosCfmExtMEPDelayHistoryForwardTotalJitter OBJECT-TYPE
 	SYNTAX			Counter64
 	MAX-ACCESS		read-only
 	STATUS			current 
 	DESCRIPTION 	
	     "This object specifies the total jitter(microseconds) seen on DMR frames received 
	      on the given service and MEP in forward direction."
 	::= { wwpLeosCfmExtMEPDelayHistoryEntry 21 }
    
  wwpLeosCfmExtMEPDelayHistoryBackwardMinJitter OBJECT-TYPE
 	SYNTAX			Unsigned32
 	MAX-ACCESS		read-only
 	STATUS			current 
 	DESCRIPTION 	
	     "This object specifies the minimum jitter(microseconds) seen on DMR frames received 
	      on the given service and MEP in backward direction."
 	::= { wwpLeosCfmExtMEPDelayHistoryEntry 22 }
   
 wwpLeosCfmExtMEPDelayHistoryBackwardMaxJitter OBJECT-TYPE
 	SYNTAX			Unsigned32
 	MAX-ACCESS		read-only
 	STATUS			current 
 	DESCRIPTION 	
	     "This object specifies the maximum jitter(microseconds) seen on DMR frames received 
	      on the given service and MEP in backward direction."
 	::= { wwpLeosCfmExtMEPDelayHistoryEntry 23 }

 wwpLeosCfmExtMEPDelayHistoryBackwardAveJitter OBJECT-TYPE
 	SYNTAX			Unsigned32
 	MAX-ACCESS		read-only
 	STATUS			current 
 	DESCRIPTION 	
	     "This object specifies the average jitter(microseconds) seen on DMR frames received 
	      on the given service and MEP in backward direction."
 	::= { wwpLeosCfmExtMEPDelayHistoryEntry 24 }

 wwpLeosCfmExtMEPDelayHistoryBackwardTotalJitter OBJECT-TYPE
 	SYNTAX			Counter64
 	MAX-ACCESS		read-only
 	STATUS			current 
 	DESCRIPTION 	
	     "This object specifies the total jitter(microseconds) seen on DMR frames received 
	      on the given service and MEP in backward direction."
 	::= { wwpLeosCfmExtMEPDelayHistoryEntry 25 }

 wwpLeosCfmExtMEPDelayHistorySuspect OBJECT-TYPE
 	SYNTAX			TruthValue
 	MAX-ACCESS		read-only
 	STATUS			current 
 	DESCRIPTION 	
	     "This object indicates that there was discontinuity in DMM Performance Measurement.
	      Condition for discontinuity include:
	      a) The conducting of performance measurement is halted before the current measurement interval is completed."
 	::= { wwpLeosCfmExtMEPDelayHistoryEntry 26 }

 wwpLeosCfmExtMEPDelayHistoryForwardMinDelay OBJECT-TYPE
 	SYNTAX			Integer32
 	MAX-ACCESS		read-only
 	STATUS			current 
 	DESCRIPTION 	
	     "This object specifies the minimum delay(microseconds) seen on DMR frames received 
	      on the given service and MEP in forward direction."
 	::= { wwpLeosCfmExtMEPDelayHistoryEntry 27 }
   
 wwpLeosCfmExtMEPDelayHistoryForwardAveDelay OBJECT-TYPE
 	SYNTAX			Integer32
 	MAX-ACCESS		read-only
 	STATUS			current 
 	DESCRIPTION 	
	     "This object specifies the average delay(microseconds) seen on DMR frames received 
	      on the given service and MEP in forward direction."
 	::= { wwpLeosCfmExtMEPDelayHistoryEntry 28 }

 wwpLeosCfmExtMEPDelayHistoryForwardMaxDelay OBJECT-TYPE
 	SYNTAX			Integer32
 	MAX-ACCESS		read-only
 	STATUS			current 
 	DESCRIPTION 	
	     "This object specifies the maximum delay(microseconds) seen on DMR frames received 
	      on the given service and MEP in forward direction."
 	::= { wwpLeosCfmExtMEPDelayHistoryEntry 29 }

  wwpLeosCfmExtMEPDelayHistoryBackwardMinDelay OBJECT-TYPE
 	SYNTAX			Integer32
 	MAX-ACCESS		read-only
 	STATUS			current 
 	DESCRIPTION 	
	     "This object specifies the minimum delay(microseconds) seen on DMR frames received 
	      on the given service and MEP in backward direction."
 	::= { wwpLeosCfmExtMEPDelayHistoryEntry 30 }
   
 wwpLeosCfmExtMEPDelayHistoryBackwardAveDelay OBJECT-TYPE
 	SYNTAX			Integer32
 	MAX-ACCESS		read-only
 	STATUS			current 
 	DESCRIPTION 	
	     "This object specifies the average delay(microseconds) seen on DMR frames received 
	      on the given service and MEP in backward direction."
 	::= { wwpLeosCfmExtMEPDelayHistoryEntry 31 }

 wwpLeosCfmExtMEPDelayHistoryBackwardMaxDelay OBJECT-TYPE
 	SYNTAX			Integer32
 	MAX-ACCESS		read-only
 	STATUS			current 
 	DESCRIPTION 	
	     "This object specifies the maximum delay(microseconds) seen on DMR frames received 
	      on the given service and MEP in backward direction."
 	::= { wwpLeosCfmExtMEPDelayHistoryEntry 32 }

--
-- CFM MEP Delay Bin History Table
--

 wwpLeosCfmExtMEPDelayBinHistoryTable OBJECT-TYPE
     SYNTAX       SEQUENCE OF WwpLeosCfmExtMEPDelayBinHistoryEntry
     MAX-ACCESS   not-accessible
     STATUS       current
     DESCRIPTION  "The (conceptual) table listing the Y.1731 Delay
                   Bin History table for the CFM MEP."  
     ::= { wwpLeosCfmExtMEP 6 }
                
 wwpLeosCfmExtMEPDelayBinHistoryEntry OBJECT-TYPE
     SYNTAX       WwpLeosCfmExtMEPDelayBinHistoryEntry
     MAX-ACCESS   not-accessible
     STATUS       current
     DESCRIPTION  "An entry (conceptual row) in the wwpLeosCfmMEPDelayBinHistoryTable."
     INDEX {wwpLeosCfmServiceIndex, wwpLeosCfmExtMEPId, wwpLeosCfmExtMEPDelayHistoryIndex, wwpLeosCfmExtMEPDelayBinHistoryBinType}
     ::= { wwpLeosCfmExtMEPDelayBinHistoryTable 1 }   

  WwpLeosCfmExtMEPDelayBinHistoryEntry ::=  SEQUENCE {
     wwpLeosCfmExtMEPDelayBinHistoryBinType                            INTEGER,      
     wwpLeosCfmExtMEPDelayBinHistoryThresholdBin1                      Unsigned32,      
     wwpLeosCfmExtMEPDelayBinHistoryThresholdBin2                      Unsigned32,      
     wwpLeosCfmExtMEPDelayBinHistoryThresholdBin3                      Unsigned32,      
     wwpLeosCfmExtMEPDelayBinHistoryThresholdBin4                      Unsigned32,      
     wwpLeosCfmExtMEPDelayBinHistoryThresholdBin5                      Unsigned32,      
     wwpLeosCfmExtMEPDelayBinHistoryThresholdBin6                      Unsigned32,      
     wwpLeosCfmExtMEPDelayBinHistoryThresholdBin7                      Unsigned32,      
     wwpLeosCfmExtMEPDelayBinHistoryThresholdBin8                      Unsigned32,      
     wwpLeosCfmExtMEPDelayBinHistoryThresholdBin9                      Unsigned32,      
     wwpLeosCfmExtMEPDelayBinHistoryThresholdBin10                     Unsigned32,      
     wwpLeosCfmExtMEPDelayBinHistoryCounterBin0                        Unsigned32,      
     wwpLeosCfmExtMEPDelayBinHistoryCounterBin1                        Unsigned32,      
     wwpLeosCfmExtMEPDelayBinHistoryCounterBin2                        Unsigned32,      
     wwpLeosCfmExtMEPDelayBinHistoryCounterBin3                        Unsigned32,      
     wwpLeosCfmExtMEPDelayBinHistoryCounterBin4                        Unsigned32,      
     wwpLeosCfmExtMEPDelayBinHistoryCounterBin5                        Unsigned32,      
     wwpLeosCfmExtMEPDelayBinHistoryCounterBin6                        Unsigned32,      
     wwpLeosCfmExtMEPDelayBinHistoryCounterBin7                        Unsigned32,      
     wwpLeosCfmExtMEPDelayBinHistoryCounterBin8                        Unsigned32,      
     wwpLeosCfmExtMEPDelayBinHistoryCounterBin9                        Unsigned32,      
     wwpLeosCfmExtMEPDelayBinHistoryCounterBin10                       Unsigned32       
  }
  
  wwpLeosCfmExtMEPDelayBinHistoryBinType OBJECT-TYPE
     SYNTAX       INTEGER 
                  {
                     delay(1),
                     jitter(2),
                     forwardJitter(3),
                     backwardJitter(4)
                  }
     MAX-ACCESS   not-accessible
     STATUS       current
     DESCRIPTION  "This is the history entry index into the table. 
                   This attribute defines the Bin Type. All below attributes holds values for this bintype."
     ::= { wwpLeosCfmExtMEPDelayBinHistoryEntry 1 }
     
  wwpLeosCfmExtMEPDelayBinHistoryThresholdBin1 OBJECT-TYPE
     SYNTAX       Unsigned32 (0..2147483647)
     MAX-ACCESS   read-only
     STATUS       current
     DESCRIPTION   "The threshold for the Delay Measurement of bintype and bin1, specified
                   in microseconds.  A value of 0 disables the bin. "
     ::= { wwpLeosCfmExtMEPDelayBinHistoryEntry 2 }

  wwpLeosCfmExtMEPDelayBinHistoryThresholdBin2 OBJECT-TYPE
     SYNTAX       Unsigned32 (0..2147483647)
     MAX-ACCESS   read-only
     STATUS       current
     DESCRIPTION   "The threshold for the Delay Measurement of bintype and bin2, specified
                   in microseconds.  A value of 0 disables the bin. "
     ::= { wwpLeosCfmExtMEPDelayBinHistoryEntry 3 }

  wwpLeosCfmExtMEPDelayBinHistoryThresholdBin3 OBJECT-TYPE
     SYNTAX       Unsigned32 (0..2147483647)
     MAX-ACCESS   read-only
     STATUS       current
     DESCRIPTION   "The threshold for the Delay Measurement of bintype and bin3, specified
                   in microseconds.  A value of 0 disables the bin. "
     ::= { wwpLeosCfmExtMEPDelayBinHistoryEntry 4 }

  wwpLeosCfmExtMEPDelayBinHistoryThresholdBin4 OBJECT-TYPE
     SYNTAX       Unsigned32 (0..2147483647)
     MAX-ACCESS   read-only
     STATUS       current
     DESCRIPTION   "The threshold for the Delay Measurement of bintype and bin4, specified
                   in microseconds.  A value of 0 disables the bin. "
     ::= { wwpLeosCfmExtMEPDelayBinHistoryEntry 5 }

  wwpLeosCfmExtMEPDelayBinHistoryThresholdBin5 OBJECT-TYPE
     SYNTAX       Unsigned32 (0..2147483647)
     MAX-ACCESS   read-only
     STATUS       current
     DESCRIPTION   "The threshold for the Delay Measurement of bintype and bin5, specified
                   in microseconds.  A value of 0 disables the bin. "
     ::= { wwpLeosCfmExtMEPDelayBinHistoryEntry 6 }


  wwpLeosCfmExtMEPDelayBinHistoryThresholdBin6 OBJECT-TYPE
     SYNTAX       Unsigned32 (0..2147483647)
     MAX-ACCESS   read-only
     STATUS       current
     DESCRIPTION   "The threshold for the Delay Measurement of bintype and bin6, specified
                   in microseconds.  A value of 0 disables the bin. "
     ::= { wwpLeosCfmExtMEPDelayBinHistoryEntry 7 }

  wwpLeosCfmExtMEPDelayBinHistoryThresholdBin7 OBJECT-TYPE
     SYNTAX       Unsigned32 (0..2147483647)
     MAX-ACCESS   read-only
     STATUS       current
     DESCRIPTION   "The threshold for the Delay Measurement of bintype and bin7, specified
                   in microseconds.  A value of 0 disables the bin. "
     ::= { wwpLeosCfmExtMEPDelayBinHistoryEntry 8 }

  wwpLeosCfmExtMEPDelayBinHistoryThresholdBin8 OBJECT-TYPE
     SYNTAX       Unsigned32 (0..2147483647)
     MAX-ACCESS   read-only
     STATUS       current
     DESCRIPTION   "The threshold for the Delay Measurement of bintype and bin8, specified
                   in microseconds.  A value of 0 disables the bin. "
     ::= { wwpLeosCfmExtMEPDelayBinHistoryEntry 9 }

  wwpLeosCfmExtMEPDelayBinHistoryThresholdBin9 OBJECT-TYPE
     SYNTAX       Unsigned32 (0..2147483647)
     MAX-ACCESS   read-only
     STATUS       current
     DESCRIPTION   "The threshold for the Delay Measurement of bintype and bin9, specified
                   in microseconds.  A value of 0 disables the bin. "
     ::= { wwpLeosCfmExtMEPDelayBinHistoryEntry 10 }

  wwpLeosCfmExtMEPDelayBinHistoryThresholdBin10 OBJECT-TYPE
     SYNTAX       Unsigned32 (0..2147483647)
     MAX-ACCESS   read-only
     STATUS       current
     DESCRIPTION   "The threshold for the Delay Measurement of bintype and bin10, specified
                   in microseconds.  A value of 0 disables the bin. "
     ::= { wwpLeosCfmExtMEPDelayBinHistoryEntry 11 }

  wwpLeosCfmExtMEPDelayBinHistoryCounterBin0 OBJECT-TYPE
     SYNTAX       Unsigned32
     MAX-ACCESS   read-only
     STATUS       current
     DESCRIPTION  "This object counters the number of frame delay measurements whose measured bintype attribute falls into a threshold range Bin 0."
     ::= { wwpLeosCfmExtMEPDelayBinHistoryEntry 12 }

  wwpLeosCfmExtMEPDelayBinHistoryCounterBin1 OBJECT-TYPE
     SYNTAX       Unsigned32
     MAX-ACCESS   read-only
     STATUS       current
     DESCRIPTION  "This object counters the number of frame delay measurements whose measured bintype attribute falls into a threshold range Bin 1."
     ::= { wwpLeosCfmExtMEPDelayBinHistoryEntry 13 }

  wwpLeosCfmExtMEPDelayBinHistoryCounterBin2 OBJECT-TYPE
     SYNTAX       Unsigned32
     MAX-ACCESS   read-only
     STATUS       current
     DESCRIPTION  "This object counters the number of frame delay measurements whose measured bintype attribute falls into a threshold range Bin 2."
     ::= { wwpLeosCfmExtMEPDelayBinHistoryEntry 14 }

  wwpLeosCfmExtMEPDelayBinHistoryCounterBin3 OBJECT-TYPE
     SYNTAX       Unsigned32
     MAX-ACCESS   read-only
     STATUS       current
     DESCRIPTION  "This object counters the number of frame delay measurements whose measured bintype attribute falls into a threshold range Bin 3."
     ::= { wwpLeosCfmExtMEPDelayBinHistoryEntry 15 }

  wwpLeosCfmExtMEPDelayBinHistoryCounterBin4 OBJECT-TYPE
     SYNTAX       Unsigned32
     MAX-ACCESS   read-only
     STATUS       current
     DESCRIPTION  "This object counters the number of frame delay measurements whose measured bintype attribute falls into a threshold range Bin 4."
     ::= { wwpLeosCfmExtMEPDelayBinHistoryEntry 16 }

  wwpLeosCfmExtMEPDelayBinHistoryCounterBin5 OBJECT-TYPE
     SYNTAX       Unsigned32
     MAX-ACCESS   read-only
     STATUS       current
     DESCRIPTION  "This object counters the number of frame delay measurements whose measured bintype attribute falls into a threshold range Bin 5."
     ::= { wwpLeosCfmExtMEPDelayBinHistoryEntry 17 }

  wwpLeosCfmExtMEPDelayBinHistoryCounterBin6 OBJECT-TYPE
     SYNTAX       Unsigned32
     MAX-ACCESS   read-only
     STATUS       current
     DESCRIPTION  "This object counters the number of frame delay measurements whose measured bintype attribute falls into a threshold range Bin 6."
     ::= { wwpLeosCfmExtMEPDelayBinHistoryEntry 18 }

  wwpLeosCfmExtMEPDelayBinHistoryCounterBin7 OBJECT-TYPE
     SYNTAX       Unsigned32
     MAX-ACCESS   read-only
     STATUS       current
     DESCRIPTION  "This object counters the number of frame delay measurements whose measured bintype attribute falls into a threshold range Bin 7."
     ::= { wwpLeosCfmExtMEPDelayBinHistoryEntry 19 }

  wwpLeosCfmExtMEPDelayBinHistoryCounterBin8 OBJECT-TYPE
     SYNTAX       Unsigned32
     MAX-ACCESS   read-only
     STATUS       current
     DESCRIPTION  "This object counters the number of frame delay measurements whose measured bintype attribute falls into a threshold range Bin 8."
     ::= { wwpLeosCfmExtMEPDelayBinHistoryEntry 20 }

  wwpLeosCfmExtMEPDelayBinHistoryCounterBin9 OBJECT-TYPE
     SYNTAX       Unsigned32
     MAX-ACCESS   read-only
     STATUS       current
     DESCRIPTION  "This object counters the number of frame delay measurements whose measured bintype attribute falls into a threshold range Bin 9."
     ::= { wwpLeosCfmExtMEPDelayBinHistoryEntry 21 }

  wwpLeosCfmExtMEPDelayBinHistoryCounterBin10 OBJECT-TYPE
     SYNTAX       Unsigned32
     MAX-ACCESS   read-only
     STATUS       current
     DESCRIPTION  "This object counters the number of frame delay measurements whose measured bintype attribute falls into a threshold range Bin 10."
     ::= { wwpLeosCfmExtMEPDelayBinHistoryEntry 22 }

 --
 --  Link Trace Message table
 --  
 wwpLeosCfmExtLinkTraceMsgTable OBJECT-TYPE
     SYNTAX     SEQUENCE OF WwpLeosCfmExtLinkTraceMsgEntry
     MAX-ACCESS not-accessible
     STATUS     current
     DESCRIPTION
            "The (conceptual) table listing the configuration
            parameters for the LinkTraceMsg."  
     ::= { wwpLeosCfmExtLinkTrace 1 }
                
 wwpLeosCfmExtLinkTraceMsgEntry OBJECT-TYPE
     SYNTAX      WwpLeosCfmExtLinkTraceMsgEntry
     MAX-ACCESS  not-accessible
     STATUS      current
     DESCRIPTION
           "An entry (conceptual row) in the wwpLeosCfmLinkTraceMsgTable."
     INDEX {wwpLeosCfmServiceIndex, wwpLeosCfmExtLinkTraceMsgLocalMepID}
     ::= { wwpLeosCfmExtLinkTraceMsgTable 1 }
                                                                     
 WwpLeosCfmExtLinkTraceMsgEntry ::=  SEQUENCE {                      
     wwpLeosCfmExtLinkTraceMsgLocalMepID		    INTEGER, 
--     wwpLeosCfmExtLinkTraceMsgPortId             	INTEGER,
     wwpLeosCfmExtLinkTraceMsgTargetMEPID        	INTEGER,
     wwpLeosCfmExtLinkTraceMsgTargetMacAddr      	MacAddress,
     wwpLeosCfmExtLinkTraceMsgTTL                	INTEGER,
     wwpLeosCfmExtLinkTraceMsgSequenceNumber       Integer32,
     wwpLeosCfmExtLinkTraceMsgPriority             INTEGER,
     wwpLeosCfmExtLinkTraceMsgAction 			   SendState   
 }
  
 wwpLeosCfmExtLinkTraceMsgLocalMepID OBJECT-TYPE
     SYNTAX INTEGER (1..8191)
     MAX-ACCESS not-accessible
     STATUS current
     DESCRIPTION
     		"This represents the local mepid."
     ::= { wwpLeosCfmExtLinkTraceMsgEntry 1}
 
-- wwpLeosCfmExtLinkTraceMsgPortId OBJECT-TYPE
--     SYNTAX       INTEGER (1..65535)
--     MAX-ACCESS   read-only
--     STATUS       current
--     DESCRIPTION
--             "This object specifies the port."
--     ::= { wwpLeosCfmExtLinkTraceMsgEntry 1 }
 
 wwpLeosCfmExtLinkTraceMsgTargetMEPID OBJECT-TYPE
     SYNTAX       INTEGER (1..8191)
     MAX-ACCESS   read-create
     STATUS       current
     DESCRIPTION
             "This object specifies the target MEPID.  This object should only be set if
	     wwpLeosCfmLinkTraceMsgTargetMacAddr is not specified else an error is returned."
     ::= { wwpLeosCfmExtLinkTraceMsgEntry 2 }
     
 wwpLeosCfmExtLinkTraceMsgTargetMacAddr OBJECT-TYPE
     SYNTAX       MacAddress
     MAX-ACCESS   read-create
     STATUS       current
     DESCRIPTION
             "This object specifies the target MAC address to be used when sending link LinkMsg.
              This object should only be set if wwpLeosCfmLinkTraceMsgTargetMEPID is not specified else
              an error is returned."
     ::= { wwpLeosCfmExtLinkTraceMsgEntry 3 }
     
 wwpLeosCfmExtLinkTraceMsgTTL OBJECT-TYPE
     SYNTAX       INTEGER (1..255)
     MAX-ACCESS   read-create
     STATUS       current
     DESCRIPTION
             "This object specifies the TTL to be used when sending LinkTraceMsg."
     ::= { wwpLeosCfmExtLinkTraceMsgEntry 4 }
 
 wwpLeosCfmExtLinkTraceMsgSequenceNumber OBJECT-TYPE
     SYNTAX       Integer32
     MAX-ACCESS   read-only
     STATUS       current
     DESCRIPTION
             "This object specifies the sequence number in the linkTraceMsg."
     ::= { wwpLeosCfmExtLinkTraceMsgEntry 5 }

 wwpLeosCfmExtLinkTraceMsgPriority OBJECT-TYPE
 	SYNTAX		INTEGER (0..7)
 	MAX-ACCESS	read-create
 	STATUS		current
 	DESCRIPTION                          
             "This object specifies the priority to be used when sending LinkTraceMsg."
 	::= { wwpLeosCfmExtLinkTraceMsgEntry 6 }  
 	
 wwpLeosCfmExtLinkTraceMsgAction  OBJECT-TYPE
    SYNTAX   SendState
    MAX-ACCESS   read-create
    STATUS       current
    DESCRIPTION
             "This object represents the action for the message (send, clear or cancel)
             If set to send(1) and if wwpLeosCfmExtLinkTraceMsgTargetMacAddr is specified
             then LinkTraceMsg is sent to remote MAC.
             If set to send(1) and if wwpLeosCfmExtLinkTraceMsgTargetMEPID is specified
             then LinktraceMsg is sent to remote mepid.
             Setting to clear(2) clears mep statistics for given service and mepid.
             Setting to cancel(3) returns commit_failed_error. "
   ::= {wwpLeosCfmExtLinkTraceMsgEntry 7}     
   
 --
 --  Link Trace Message Reply table
 --  
 wwpLeosCfmExtLinkTraceMsgReplyTable OBJECT-TYPE
     SYNTAX     SEQUENCE OF WwpLeosCfmExtLinkTraceMsgReplyEntry
     MAX-ACCESS not-accessible
     STATUS     current
     DESCRIPTION
            "The (conceptual) table listing the display
            parameters for the LinkTrace Msg Reply."  
     ::= { wwpLeosCfmExtLinkTrace 2 }
                
  wwpLeosCfmExtLinkTraceMsgReplyEntry OBJECT-TYPE
     SYNTAX      WwpLeosCfmExtLinkTraceMsgReplyEntry
     MAX-ACCESS  not-accessible
     STATUS      current
     DESCRIPTION
           "An entry (conceptual row) in the wwpLeosCfmExtLinkTraceMsgReplyTable."
     INDEX {wwpLeosCfmServiceIndex, wwpLeosCfmExtLinkTraceMsgLocalMepID, wwpLeosCfmExtLinkTraceMsgReplyTTL, wwpLeosCfmExtLinkTraceMsgReplyTTLIndex}
     ::= { wwpLeosCfmExtLinkTraceMsgReplyTable 1 }
                
  WwpLeosCfmExtLinkTraceMsgReplyEntry ::=  SEQUENCE {           
         wwpLeosCfmExtLinkTraceMsgReplyTTL                      	Integer32,
         wwpLeosCfmExtLinkTraceMsgReplyTTLIndex                    	Unsigned32,
         wwpLeosCfmExtLinkTraceMsgReplySequenceNumber              	Integer32,
         wwpLeosCfmExtLinkTraceMsgReplyMPMacAddr                   	MacAddress,
         wwpLeosCfmExtLinkTraceMsgReplyMEPID                       	Integer32,
         wwpLeosCfmExtLinkTraceMsgReplyTargetMacAddr               	MacAddress,
         wwpLeosCfmExtLinkTraceMsgReplyRelayAction 					INTEGER,
         wwpLeosCfmExtLinkTraceMsgReplyIngressPort   				INTEGER,
         wwpLeosCfmExtLinkTraceMsgReplyIngressAction   				INTEGER,
         wwpLeosCfmExtLinkTraceMsgReplyEgressPort   				INTEGER,
         wwpLeosCfmExtLinkTraceMsgReplyEgressAction 				INTEGER,
         wwpLeosCfmExtLinkTraceMsgReplyIngressPortStr				DisplayString,
         wwpLeosCfmExtLinkTraceMsgReplyEgressPortStr				DisplayString                
  }   
  
  wwpLeosCfmExtLinkTraceMsgReplyTTL OBJECT-TYPE
     SYNTAX       Integer32 (0..255)
     MAX-ACCESS   read-only
     STATUS       current
     DESCRIPTION
             "This object specifies the TTL of the received LinkTrace msg reply."
     ::= { wwpLeosCfmExtLinkTraceMsgReplyEntry 1 }
     
  wwpLeosCfmExtLinkTraceMsgReplyTTLIndex OBJECT-TYPE
     SYNTAX       Unsigned32 (1..24576)
     MAX-ACCESS   read-only
     STATUS       current
     DESCRIPTION
             "This object provides an additional index when multiple LinkTrace messages are received with the same TTL."
     ::= { wwpLeosCfmExtLinkTraceMsgReplyEntry 2 }
  
  wwpLeosCfmExtLinkTraceMsgReplySequenceNumber OBJECT-TYPE
     SYNTAX       Integer32
     MAX-ACCESS   read-only
     STATUS       current
     DESCRIPTION
             "This object specifies the sequence number of the received LinkTrace msg reply."
     ::= { wwpLeosCfmExtLinkTraceMsgReplyEntry 3 }

  wwpLeosCfmExtLinkTraceMsgReplyMPMacAddr OBJECT-TYPE
     SYNTAX       MacAddress
     MAX-ACCESS   read-only
     STATUS       current
     DESCRIPTION
             "This object specifies the MAC address of the MP of the received LinkTrace msg reply."
     ::= { wwpLeosCfmExtLinkTraceMsgReplyEntry 4 }

  wwpLeosCfmExtLinkTraceMsgReplyMEPID OBJECT-TYPE
     SYNTAX       Integer32
     MAX-ACCESS   read-only
     STATUS       current
     DESCRIPTION
             "This object specifies the MEP ID of the received LinkTrace msg reply."
     ::= { wwpLeosCfmExtLinkTraceMsgReplyEntry 5 }

  wwpLeosCfmExtLinkTraceMsgReplyTargetMacAddr OBJECT-TYPE
     SYNTAX       MacAddress
     MAX-ACCESS   read-only
     STATUS       current
     DESCRIPTION
             "This object specifies the target MAC address of the received LinkTrace msg reply."
     ::= { wwpLeosCfmExtLinkTraceMsgReplyEntry 6 }
     
  wwpLeosCfmExtLinkTraceMsgReplyRelayAction OBJECT-TYPE
     SYNTAX       INTEGER   {
     					invalid(1), 
     					unknown(2),
     					fdb(3),
     					mpdb(4),
     					noLearn(5),
     					hit(6)
     				}     
     MAX-ACCESS   read-only
     STATUS       current
     DESCRIPTION
             "This object specifies the message reply relay action."
     ::= { wwpLeosCfmExtLinkTraceMsgReplyEntry 7 }
  
  wwpLeosCfmExtLinkTraceMsgReplyIngressPort  OBJECT-TYPE
     SYNTAX       INTEGER  (1..65535)
     MAX-ACCESS   read-only
     STATUS       obsolete
     DESCRIPTION
             "This object specifies the message reply ingress port."
     ::= { wwpLeosCfmExtLinkTraceMsgReplyEntry 8 }
 
  wwpLeosCfmExtLinkTraceMsgReplyIngressAction  OBJECT-TYPE
     SYNTAX       INTEGER  {
     					ok(1),
     					blocked(2),
     					vid(3),
     					down(4),
     					none(5)
     				}
     MAX-ACCESS   read-only
     STATUS       current
     DESCRIPTION
             "This object specifies the message reply ingress action."
     ::= { wwpLeosCfmExtLinkTraceMsgReplyEntry 9 }
 
  wwpLeosCfmExtLinkTraceMsgReplyEgressPort  OBJECT-TYPE
     SYNTAX       INTEGER  (1..65535)
     MAX-ACCESS   read-only
     STATUS       obsolete
     DESCRIPTION
             "This object specifies the message reply egress port."
     ::= { wwpLeosCfmExtLinkTraceMsgReplyEntry 10 }
  
  wwpLeosCfmExtLinkTraceMsgReplyEgressAction  OBJECT-TYPE
     SYNTAX       INTEGER  {
     				none(1),
     				ttl(2),
     				down(3),
     				blocked(4),
     				vid(5),
     				ok(6)
     				}
     MAX-ACCESS   read-only
     STATUS       current
     DESCRIPTION
             "This object specifies the message reply egress action."
     ::= { wwpLeosCfmExtLinkTraceMsgReplyEntry 11 } 
     
 wwpLeosCfmExtLinkTraceMsgReplyIngressPortStr OBJECT-TYPE
     SYNTAX       DisplayString (SIZE(1..8))
     MAX-ACCESS   read-only
     STATUS       current
     DESCRIPTION
             "This MIB object specifies the message reply ingress port."
     ::= { wwpLeosCfmExtLinkTraceMsgReplyEntry 12 }        
 
 wwpLeosCfmExtLinkTraceMsgReplyEgressPortStr OBJECT-TYPE
     SYNTAX       DisplayString (SIZE(1..8))
     MAX-ACCESS   read-only
     STATUS       current
     DESCRIPTION
             "This MIB object specifies the message reply egress port."
     ::= { wwpLeosCfmExtLinkTraceMsgReplyEntry 13 } 
 --
  -- Delay Measurement Msg table
  -- 
  wwpLeosCfmExtDelayMsgTable OBJECT-TYPE
     SYNTAX     SEQUENCE OF WwpLeosCfmExtDelayMsgEntry
     MAX-ACCESS not-accessible
     STATUS     current
     DESCRIPTION
            "The (conceptual) table listing the configuration
            parameters for the DelayMeasurementMsg."
            
     ::= { wwpLeosCfmExtDelay 1 }
                
 wwpLeosCfmExtDelayMsgEntry OBJECT-TYPE
     SYNTAX      WwpLeosCfmExtDelayMsgEntry
     MAX-ACCESS  not-accessible
     STATUS      current
     DESCRIPTION
           "An entry (conceptual row) in the wwpLeosCfmDelayMsgTable.
           To send, clear or cancel the message, the corresponding MsgAction
           needs to be specified. Individual objects in this table
           cannot be set.                                     
           To send or cancel a message, the TargetMepID or the
           TargtetMacAddr objects need to be specified.
           Clear msgAction clears the counters for the message."
     --wwpLeosCfmExtDelayMsgLocalMEPId is a new index in place of delayMsgPortId
     INDEX {wwpLeosCfmServiceIndex, wwpLeosCfmExtDelayMsgLocalMEPId}
     ::= { wwpLeosCfmExtDelayMsgTable 1 }
                
 WwpLeosCfmExtDelayMsgEntry ::=  SEQUENCE { 
     wwpLeosCfmExtDelayMsgLocalMEPId                  	INTEGER,
     wwpLeosCfmExtDelayMsgTargetMEPID              Unsigned32,
     wwpLeosCfmExtDelayMsgTargetMacAddr            MacAddress,
     wwpLeosCfmExtDelayMsgCount                   	INTEGER,
     wwpLeosCfmExtDelayMsgPriority                	INTEGER,
  	 wwpLeosCfmExtDelayMsgRepeat					INTEGER,
     wwpLeosCfmExtDelayMsgRepeatCount				INTEGER,
     wwpLeosCfmExtDelayMsgDelayThreshold			INTEGER,
     wwpLeosCfmExtDelayMsgJitterThreshold			INTEGER,
     wwpLeosCfmExtDelayMsgAction				    SendState,
     wwpLeosCfmExtDelayMsgMaxDelayThreshold			INTEGER,
     wwpLeosCfmExtDelayMsgMaxJitterThreshold		INTEGER,
     wwpLeosCfmExtDelayMsgDelayProfile		        Unsigned32,
     wwpLeosCfmExtDelayMsgJitterProfile		        Unsigned32,
     wwpLeosCfmExtDelayMsgForwardJitterProfile		Unsigned32,
     wwpLeosCfmExtDelayMsgBackwardJitterProfile		Unsigned32
    }

 wwpLeosCfmExtDelayMsgLocalMEPId OBJECT-TYPE
     SYNTAX       INTEGER (1..65535)
     MAX-ACCESS   not-accessible
     STATUS       current
     DESCRIPTION
             "This object specifies the local MEPID."
     ::= { wwpLeosCfmExtDelayMsgEntry 1 }
 
 wwpLeosCfmExtDelayMsgTargetMEPID OBJECT-TYPE
     SYNTAX       Unsigned32 (1..8191)
     MAX-ACCESS   read-create
     STATUS       current
     DESCRIPTION
             "This object specifies the MEPID.
              This object should only be set if wwpLeosCfmExtDelayMsgTargetMacAddr is not specified else
              an error is returned."
     ::= { wwpLeosCfmExtDelayMsgEntry 2 }
     
 wwpLeosCfmExtDelayMsgTargetMacAddr OBJECT-TYPE
     SYNTAX       MacAddress
     MAX-ACCESS   read-create
     STATUS       current
     DESCRIPTION
             "This object specifies the MacAddress to be used when sending link LoopbackMsg.
              This object should only be set if wwpLeosCfmExtDelayMsgTargetMEPID is not specified else
              an error is returned."
     ::= {wwpLeosCfmExtDelayMsgEntry 3 }
     
 wwpLeosCfmExtDelayMsgCount OBJECT-TYPE
     SYNTAX       INTEGER (0 | 2..600) 
     MAX-ACCESS   read-create
     STATUS       current
     DESCRIPTION
              "This object specifies the DelayMeasurementMsg count to be used
              when sending link DelayMeasurementMsg. Counts between 2 and 600 are valid. The system 
              default count is used if a value of 0 is entered."
     ::= { wwpLeosCfmExtDelayMsgEntry 4 }
 
 wwpLeosCfmExtDelayMsgPriority OBJECT-TYPE
     SYNTAX       INTEGER (0..7)
     MAX-ACCESS   read-create
     STATUS       current
     DESCRIPTION
             "This object specifies the DelayMeasurementMsg priority to be
             used when sending link DelayMeasurementMsg."
     ::= { wwpLeosCfmExtDelayMsgEntry 5 }
 
 
  wwpLeosCfmExtDelayMsgRepeat OBJECT-TYPE
 	 SYNTAX			INTEGER {
 	 					enable(1),
 	 					disable(2)
 	 					}
 	 MAX-ACCESS		read-create
 	 STATUS			current
 	 DESCRIPTION
 	 		"Used to make the Delay Measurement test a repeating test."
 	 ::= { wwpLeosCfmExtDelayMsgEntry 8 } 
 	 
 wwpLeosCfmExtDelayMsgRepeatCount OBJECT-TYPE
 	SYNTAX			INTEGER (0..1440)
 	MAX-ACCESS		read-create
 	STATUS			current
 	DESCRIPTION
 			"This object specifies the repeat time in minutes for the Delay Measurement test.
 			If zero is specified, the test runs continuously."
 	::= { wwpLeosCfmExtDelayMsgEntry 9 }  

   wwpLeosCfmExtDelayMsgDelayThreshold OBJECT-TYPE
     SYNTAX       INTEGER (-1..2147483647)
     MAX-ACCESS   read-create
     STATUS       current
     DESCRIPTION
              "This object specifies represents the fault Threshold for the average delay, specified
              in microseconds.  A value of -1 disables the generatation of faults. A value of
              0 or greater is compared to the average delay result of the
              test and a fault is generated if the threshold is exceeded."
     ::= {wwpLeosCfmExtDelayMsgEntry 41 }
  
  wwpLeosCfmExtDelayMsgJitterThreshold OBJECT-TYPE
     SYNTAX       INTEGER  (-1..2147483647)
     MAX-ACCESS   read-create
     STATUS       current
     DESCRIPTION
              "This object specifies represents the fault threshold value for the average Jitter, specified
              in microseconds.  A value of -1 disables the generation of faults. A value of
              0 or greater is compared to the average jitter result of the
              test and a fault is generated if the threshold is exceeded."
     ::= { wwpLeosCfmExtDelayMsgEntry 42 }  
   
  wwpLeosCfmExtDelayMsgAction OBJECT-TYPE
     SYNTAX       SendState
     MAX-ACCESS   read-create
     STATUS       current
     DESCRIPTION
             "This object represents the action for the message (send, clear or cancel)
             If set to send(1) and if wwpLeosCfmExtDelayMsgTargetMacAddr is specified
             then loopbackMsg is sent to remote MAC.
             If set to send(1) and if wwpLeosCfmExtDelayMsgTargetMEPID is specified
             then loopbackMsg is sent to remote mepid.
             Setting to clear(2) clears mep statistics for given service and mepid.
             If set to cancel(3) and if wwpLeosCfmExtDelayMsgTargetMacAddr is specified 
             then it cancels sending Delay messages to remoteMac.
             If set to cancel(3) and if wwpLeosCfmExtDelayMsgTargetMEPID is specified 
             then it cancels sending Delay messages to remoteMEPID."
     ::= { wwpLeosCfmExtDelayMsgEntry 43 }
  
  wwpLeosCfmExtDelayMsgMaxDelayThreshold OBJECT-TYPE
     SYNTAX       INTEGER (-1..2147483647)
     MAX-ACCESS   read-create
     STATUS       current
     DESCRIPTION
              "This object represents the threshold for the maximum Delay, specified
              in microseconds.  A value of -1 disables the generatation of faults.
              A value of 0 or greater is compared to the maximum delay result of the
              test and a fault is generated if the threshold is exceeded."
     ::= {wwpLeosCfmExtDelayMsgEntry 44 }
  
  wwpLeosCfmExtDelayMsgMaxJitterThreshold OBJECT-TYPE
     SYNTAX       INTEGER  (-1..2147483647)
     MAX-ACCESS   read-create
     STATUS       current
     DESCRIPTION
              "This object represents the threshold value for the maximum Jitter, specified
              in microseconds.  A value of -1 disables the generatation of faults.
              A value of 0 or greater is compared to the maximum jitter result of the
              test and a fault is generated if the threshold is exceeded."
     ::= { wwpLeosCfmExtDelayMsgEntry 45 }  
 wwpLeosCfmExtDelayMsgDelayProfile OBJECT-TYPE
        SYNTAX                  Unsigned32 (1..4096)
        MAX-ACCESS              read-create
        STATUS                  current
        DESCRIPTION
                        "The delay profile index. The default value is 1."
     ::= { wwpLeosCfmExtDelayMsgEntry 46 }
 wwpLeosCfmExtDelayMsgJitterProfile OBJECT-TYPE
        SYNTAX                  Unsigned32 (1..4096)
        MAX-ACCESS              read-create
        STATUS                  current
        DESCRIPTION
                        "The jitter profile index. The default value is 1."
      ::= { wwpLeosCfmExtDelayMsgEntry 47 }

 wwpLeosCfmExtDelayMsgForwardJitterProfile OBJECT-TYPE
        SYNTAX                  Unsigned32 (1..4096)
        MAX-ACCESS              read-create
        STATUS                  current
        DESCRIPTION
                        "The jitter profile index for one way dmm forward direction. The default value is 1."
      ::= { wwpLeosCfmExtDelayMsgEntry 48 }

 wwpLeosCfmExtDelayMsgBackwardJitterProfile OBJECT-TYPE
        SYNTAX                  Unsigned32 (1..4096)
        MAX-ACCESS              read-create
        STATUS                  current
        DESCRIPTION
                        "The jitter profile index for one way dmm backward direction. The default value is 1."
      ::= { wwpLeosCfmExtDelayMsgEntry 49 }

  --
  -- Delay Measurement Msg table
  -- 
  wwpLeosCfmExtDelaySessionTable OBJECT-TYPE
     SYNTAX     SEQUENCE OF WwpLeosCfmExtDelaySessionEntry
     MAX-ACCESS not-accessible
     STATUS     current
     DESCRIPTION
            "The (conceptual) table lists the configuration
            parameters for a DMM session."            
     ::= { wwpLeosCfmExtDelay 2 }      
     
  wwpLeosCfmExtDelaySessionEntry OBJECT-TYPE
     SYNTAX      WwpLeosCfmExtDelaySessionEntry
     MAX-ACCESS  not-accessible
     STATUS      current
     DESCRIPTION
           "An entry (conceptual row) in the wwpLeosCfmExtDelaySessionTable.
           To send, clear or cancel the message, the corresponding MsgAction
           needs to be specified. Individual objects in this table
           cannot be set."      
     INDEX {wwpLeosCfmServiceIndex, wwpLeosCfmExtMEPId,wwpLeosCfmRemoteMEPID,
            wwpLeosCfmExtDelaySessionTestId}
     ::= { wwpLeosCfmExtDelaySessionTable 1 }  
     
  WwpLeosCfmExtDelaySessionEntry ::=  SEQUENCE {  
     wwpLeosCfmExtDelaySessionTestId                Unsigned32,
     wwpLeosCfmExtDelaySessionPriority              Unsigned32,
     wwpLeosCfmExtDelaySessionCount                 Unsigned32,     
	 wwpLeosCfmExtDelaySessionDMMInterval           Unsigned32,
  	 wwpLeosCfmExtDelaySessionIterations		    Unsigned32,
     wwpLeosCfmExtDelaySessionRepeatDelay			Unsigned32, 
     wwpLeosCfmExtDelaySessionFrameSize             Unsigned32,
     wwpLeosCfmExtDelaySessionTimeout               Unsigned32,
     wwpLeosCfmExtDelaySessionDuration				Unsigned32,
     wwpLeosCfmExtDelaySessionDelayThreshold		Integer32,
     wwpLeosCfmExtDelaySessionJitterThreshold		Integer32,
     wwpLeosCfmExtDelaySessionMaxDelayThreshold		Integer32,
     wwpLeosCfmExtDelaySessionMaxJitterThreshold	Integer32,  
     wwpLeosCfmExtDelaySessionAccelerated           TruthValue,
	 wwpLeosCfmExtDelaySessionAction				SendState,
	 wwpLeosCfmExtDelaySessionNumDMMSent		    Unsigned32,
  	 wwpLeosCfmExtDelaySessionNumDMRReceived		Unsigned32,
  	 wwpLeosCfmExtDelaySessionMinDelay				Unsigned32,
  	 wwpLeosCfmExtDelaySessionAvgDelay				Unsigned32,
  	 wwpLeosCfmExtDelaySessionMaxDelay				Unsigned32, 
  	 wwpLeosCfmExtDelaySessionMinJitter				Unsigned32,
  	 wwpLeosCfmExtDelaySessionAvgJitter				Unsigned32,
  	 wwpLeosCfmExtDelaySessionMaxJitter				Unsigned32,
      wwpLeosCfmExtDelaySessionDelayCounterBin0                         Unsigned32,
      wwpLeosCfmExtDelaySessionDelayCounterBin1                         Unsigned32,
      wwpLeosCfmExtDelaySessionDelayCounterBin2                         Unsigned32,
      wwpLeosCfmExtDelaySessionDelayCounterBin3                         Unsigned32,
      wwpLeosCfmExtDelaySessionDelayCounterBin4                         Unsigned32,
      wwpLeosCfmExtDelaySessionDelayCounterBin5                         Unsigned32,
      wwpLeosCfmExtDelaySessionDelayCounterBin6                         Unsigned32,
      wwpLeosCfmExtDelaySessionDelayCounterBin7                         Unsigned32,
      wwpLeosCfmExtDelaySessionDelayCounterBin8                         Unsigned32,
      wwpLeosCfmExtDelaySessionDelayCounterBin9                         Unsigned32,
      wwpLeosCfmExtDelaySessionDelayCounterBin10                        Unsigned32,
      wwpLeosCfmExtDelaySessionJitterCounterBin0                        Unsigned32,
      wwpLeosCfmExtDelaySessionJitterCounterBin1                        Unsigned32,
      wwpLeosCfmExtDelaySessionJitterCounterBin2                        Unsigned32,
      wwpLeosCfmExtDelaySessionJitterCounterBin3                        Unsigned32,
      wwpLeosCfmExtDelaySessionJitterCounterBin4                        Unsigned32,
      wwpLeosCfmExtDelaySessionJitterCounterBin5                        Unsigned32,
      wwpLeosCfmExtDelaySessionJitterCounterBin6                        Unsigned32,
      wwpLeosCfmExtDelaySessionJitterCounterBin7                        Unsigned32,
      wwpLeosCfmExtDelaySessionJitterCounterBin8                        Unsigned32,
      wwpLeosCfmExtDelaySessionJitterCounterBin9                        Unsigned32,
      wwpLeosCfmExtDelaySessionJitterCounterBin10                       Unsigned32,
      wwpLeosCfmExtDelaySessionConfigAccelerated                        TruthValue,
      wwpLeosCfmExtDelaySessionDelayProfile                             Unsigned32,
      wwpLeosCfmExtDelaySessionJitterProfile                            Unsigned32,
      wwpLeosCfmExtDelaySessionTotalJitter                              Counter64,
      wwpLeosCfmExtDelaySessionForwardMinJitter                         Unsigned32,
      wwpLeosCfmExtDelaySessionForwardMaxJitter                         Unsigned32,
      wwpLeosCfmExtDelaySessionForwardAvgJitter                         Unsigned32,
      wwpLeosCfmExtDelaySessionForwardTotalJitter                       Counter64,
      wwpLeosCfmExtDelaySessionBackwardMinJitter                        Unsigned32,
      wwpLeosCfmExtDelaySessionBackwardMaxJitter                        Unsigned32,
      wwpLeosCfmExtDelaySessionBackwardAvgJitter                        Unsigned32,
      wwpLeosCfmExtDelaySessionBackwardTotalJitter                      Counter64,
      wwpLeosCfmExtDelaySessionForwardJitterCounterBin0                 Unsigned32,
      wwpLeosCfmExtDelaySessionForwardJitterCounterBin1                 Unsigned32,
      wwpLeosCfmExtDelaySessionForwardJitterCounterBin2                 Unsigned32,
      wwpLeosCfmExtDelaySessionForwardJitterCounterBin3                 Unsigned32,
      wwpLeosCfmExtDelaySessionForwardJitterCounterBin4                 Unsigned32,
      wwpLeosCfmExtDelaySessionForwardJitterCounterBin5                 Unsigned32,
      wwpLeosCfmExtDelaySessionForwardJitterCounterBin6                 Unsigned32,
      wwpLeosCfmExtDelaySessionForwardJitterCounterBin7                 Unsigned32,
      wwpLeosCfmExtDelaySessionForwardJitterCounterBin8                 Unsigned32,
      wwpLeosCfmExtDelaySessionForwardJitterCounterBin9                 Unsigned32,
      wwpLeosCfmExtDelaySessionForwardJitterCounterBin10                Unsigned32,
      wwpLeosCfmExtDelaySessionBackwardJitterCounterBin0                Unsigned32,
      wwpLeosCfmExtDelaySessionBackwardJitterCounterBin1                Unsigned32,
      wwpLeosCfmExtDelaySessionBackwardJitterCounterBin2                Unsigned32,
      wwpLeosCfmExtDelaySessionBackwardJitterCounterBin3                Unsigned32,
      wwpLeosCfmExtDelaySessionBackwardJitterCounterBin4                Unsigned32,
      wwpLeosCfmExtDelaySessionBackwardJitterCounterBin5                Unsigned32,
      wwpLeosCfmExtDelaySessionBackwardJitterCounterBin6                Unsigned32,
      wwpLeosCfmExtDelaySessionBackwardJitterCounterBin7                Unsigned32,
      wwpLeosCfmExtDelaySessionBackwardJitterCounterBin8                Unsigned32,
      wwpLeosCfmExtDelaySessionBackwardJitterCounterBin9                Unsigned32,
      wwpLeosCfmExtDelaySessionBackwardJitterCounterBin10               Unsigned32,
      wwpLeosCfmExtDelaySessionSuspect                                  TruthValue,
      wwpLeosCfmExtDelaySessionForwardMinDelay                          Integer32,
      wwpLeosCfmExtDelaySessionForwardAveDelay                          Integer32,
      wwpLeosCfmExtDelaySessionForwardMaxDelay                          Integer32,
      wwpLeosCfmExtDelaySessionBackwardMinDelay                         Integer32,
      wwpLeosCfmExtDelaySessionBackwardAveDelay                         Integer32,
      wwpLeosCfmExtDelaySessionBackwardMaxDelay                         Integer32,
      wwpLeosCfmExtDelaySessionConfigTimestampType                      CfmTimestampType,
      wwpLeosCfmExtDelaySessionCosMode                                  TruthValue,
      wwpLeosCfmExtDelaySessionSdDelayClearThreshold                    Integer32,
      wwpLeosCfmExtDelaySessionSdDelaySetThreshold                      Integer32,
      wwpLeosCfmExtDelaySessionSdJitterClearThreshold                   Integer32,
      wwpLeosCfmExtDelaySessionSdJitterSetThreshold                     Integer32,
      wwpLeosCfmExtDelaySessionForwardJitterProfile                     Unsigned32,
      wwpLeosCfmExtDelaySessionBackwardJitterProfile                    Unsigned32
    }     
    
  wwpLeosCfmExtDelaySessionTestId OBJECT-TYPE
     SYNTAX       Unsigned32 (0..4294967295)
     MAX-ACCESS   not-accessible
     STATUS       current
     DESCRIPTION
              "This object specifies the DMM test ID to be used when sending DMM."
     ::= { wwpLeosCfmExtDelaySessionEntry 1 }      
     
  wwpLeosCfmExtDelaySessionPriority OBJECT-TYPE
     SYNTAX       Unsigned32 (0..7)
     MAX-ACCESS   read-write
     STATUS       current
     DESCRIPTION
             "This object specifies the DMM priority to be used when sending DMM.
	     Recommended to set this object when performing SET operation."
     ::= { wwpLeosCfmExtDelaySessionEntry 2 }  
          
 wwpLeosCfmExtDelaySessionCount OBJECT-TYPE
     SYNTAX       Unsigned32 (0 | 2..65535) 
     MAX-ACCESS   read-create
     STATUS       current
     DESCRIPTION
              "This object specifies the DMM count to be used when sending link DelayMeasurementMsg.
	      Counts between 2 and 65535 are valid. The system 
              default count is used if a value of 0 is entered."
     ::= { wwpLeosCfmExtDelaySessionEntry 3 }     
     
  wwpLeosCfmExtDelaySessionDMMInterval OBJECT-TYPE
     SYNTAX       Unsigned32 (0..7)
     MAX-ACCESS   read-write
     STATUS       current
     DESCRIPTION
             "This object specifies the DMM transmission intervals.
	      If set to Zero, CFM global default interval setting is applied.
        
              The values 1-7 represent indices to CFM intervals as follows:
              1 --> 3.33ms,
              2 --> 10ms,
              3 --> 100ms,
              4 --> 1sec,
              5 --> 10sec,
              6 --> 1min,
              7 --> 10min."
     ::= { wwpLeosCfmExtDelaySessionEntry 4 } 
     
  wwpLeosCfmExtDelaySessionIterations OBJECT-TYPE
 	 SYNTAX			Unsigned32 (0..60)
 	 MAX-ACCESS		read-create
 	 STATUS			current
 	 DESCRIPTION
 	 		"This object specifies the number of iterations the test
             has to be conducted. Each test iteration is defined by wwpLeosCfmExtDelaySessionDMMInterval,
             wwpLeosCfmExtDelaySessionCount. Whereas, the test sessions is defined by test iterations over 
             wwpLeosCfmExtDelaySessionIterations.
              
             If this object is set to zero, it means that test is continuous, and iterations are infinite. "
 	 ::= { wwpLeosCfmExtDelaySessionEntry 5 }  
 	 
  wwpLeosCfmExtDelaySessionRepeatDelay OBJECT-TYPE
 	 SYNTAX			Unsigned32 (0..1440)
 	 MAX-ACCESS		read-create
 	 STATUS			current
 	 DESCRIPTION
 			"This object specifies the delay in minutes between consecutive test iterations."
 	::= { wwpLeosCfmExtDelaySessionEntry 6 }   
 	
  wwpLeosCfmExtDelaySessionFrameSize  OBJECT-TYPE  
     SYNTAX       Unsigned32 (0 | 140..1400)
     MAX-ACCESS   read-create
     STATUS       current
     DESCRIPTION
             "This object specifies the size in bytes of the CFM Base frame.
              If this object is set to zero, there is NO padding."
     ::= { wwpLeosCfmExtDelaySessionEntry 7 }
     
  wwpLeosCfmExtDelaySessionTimeout  OBJECT-TYPE  
     SYNTAX       Unsigned32 (0 | 2000..10000)
     MAX-ACCESS   read-create
     STATUS       current
     DESCRIPTION
             "This object specifies the timeout interval in milliseconds within which
              the source should Rx a DMR for a corresponding DMM.
              If this object is set to zero, the CFM global default setting is applied."
     ::= { wwpLeosCfmExtDelaySessionEntry 8 }
     
  wwpLeosCfmExtDelaySessionDuration OBJECT-TYPE
 	 SYNTAX			Unsigned32 (0..65535)
 	 MAX-ACCESS		read-create
 	 STATUS			current                                   
 	 DESCRIPTION
 		     "The duration of time each test iteration needs to run. If this object is set
 		      wwpLeosCfmExtDelaySessionCount cannot be set."
 	 ::= { wwpLeosCfmExtDelaySessionEntry 9 }
 	 
  wwpLeosCfmExtDelaySessionDelayThreshold OBJECT-TYPE
     SYNTAX       Integer32 (-1..2147483647)
     MAX-ACCESS   read-create
     STATUS       current
     DESCRIPTION
              "This object represents the fault threshold for the average delay, specified
              in microseconds.  A value of -1 disables the generatation of faults.
              A value of 0 or greater is compared to the average delay result of the
              test and a fault is generated if the threshold is exceeded."
     ::= {wwpLeosCfmExtDelaySessionEntry 10 }  
     
  wwpLeosCfmExtDelaySessionJitterThreshold OBJECT-TYPE
     SYNTAX       Integer32  (-1..2147483647)
     MAX-ACCESS   read-create
     STATUS       current
     DESCRIPTION
              "This object represents the fault threshold value for the average Jitter, specified
              in microseconds.  A value of -1 disables the generation of faults.
              A value of 0 or greater is compared to the average jitter result of the
              test and a fault is generated if the threshold is exceeded."
     ::= { wwpLeosCfmExtDelaySessionEntry 11 } 
      
  wwpLeosCfmExtDelaySessionMaxDelayThreshold OBJECT-TYPE
     SYNTAX       Integer32 (-1..2147483647)
     MAX-ACCESS   read-create
     STATUS       current
     DESCRIPTION
              "This object represents the threshold for the maximum delay, specified
              in microseconds.  A value of -1 disables the generatation of faults.
              A value of 0 or greater is compared to the maximum delay result of the
              test and a fault is generated if the threshold is exceeded."
     ::= {wwpLeosCfmExtDelaySessionEntry 12 }  
     
  wwpLeosCfmExtDelaySessionMaxJitterThreshold OBJECT-TYPE
     SYNTAX       Integer32  (-1..2147483647)
     MAX-ACCESS   read-create
     STATUS       current
     DESCRIPTION
              "This object represents the threshold value for the maximum Jitter, specified
              in microseconds.  A value of -1 disables the generatation of faults.
              A value of 0 or greater is compared to the maximum jitter result of the
              test and a fault is generated if the threshold is exceeded."
     ::= { wwpLeosCfmExtDelaySessionEntry 13 }  
      	
  wwpLeosCfmExtDelaySessionAccelerated	OBJECT-TYPE
 	SYNTAX			TruthValue
 	MAX-ACCESS		read-create
 	STATUS			current
 	DESCRIPTION
 	     "Setting this attribute to true gathers delay measurements in hardware. 
             This object returns true if delay sender is actively utilizing hardware resources."
 	::= { wwpLeosCfmExtDelaySessionEntry 14 }   
 	
  wwpLeosCfmExtDelaySessionAction OBJECT-TYPE
     SYNTAX       SendState
     MAX-ACCESS   read-create
     STATUS       current
     DESCRIPTION
             "This object represents the action for the message (send, clear, delete or cancel)
             If set to send(1) DMM message is sent to remote mep represented by wwpLeosCfmRemoteMEPID
             with the specific test id.
             Setting to clear(2) clears mep statistics for given service and mepid.
             If set to cancel(3) test is cancelled for this specific testid.
             If set to delete(4) test is deleted for this specific testid."
     ::= { wwpLeosCfmExtDelaySessionEntry 15 } 
     
  wwpLeosCfmExtDelaySessionNumDMMSent OBJECT-TYPE
 	 SYNTAX			Unsigned32
 	 MAX-ACCESS		read-only
 	 STATUS			current 
     DESCRIPTION	
    	     "This object specifies the number of DMM frames sent during the last iteration
	     of the completed test."
     ::= { wwpLeosCfmExtDelaySessionEntry 16 }      
    
  wwpLeosCfmExtDelaySessionNumDMRReceived OBJECT-TYPE
 	 SYNTAX			Unsigned32
 	 MAX-ACCESS		read-only
 	 STATUS			current 
     DESCRIPTION	
    	     "This object specifies the number of DMR frames received during the last iteration 
             of the completed test."
     ::= { wwpLeosCfmExtDelaySessionEntry 17 } 
     
  wwpLeosCfmExtDelaySessionMinDelay OBJECT-TYPE
 	 SYNTAX			Unsigned32
 	 MAX-ACCESS		read-only
 	 STATUS			current 
     DESCRIPTION	
    	     "This object specifies the minimum delay(microseconds) seen on DMR frames received
	     during the last iteration of the completed test."
     ::= { wwpLeosCfmExtDelaySessionEntry 18 }
     
  wwpLeosCfmExtDelaySessionAvgDelay OBJECT-TYPE
 	 SYNTAX			Unsigned32
 	 MAX-ACCESS		read-only
 	 STATUS			current 
     DESCRIPTION	
    	     "This object specifies the average delay(microseconds) seen on DMR frames received
	     during the last iteration of the completed test."
     ::= { wwpLeosCfmExtDelaySessionEntry 19 }
     
  wwpLeosCfmExtDelaySessionMaxDelay OBJECT-TYPE
 	 SYNTAX			Unsigned32
 	 MAX-ACCESS		read-only
 	 STATUS			current 
     DESCRIPTION	
    	     "This object specifies the maximum delay(us) seen on DMR frames received
	     during the last iteration of the completed test."
     ::= { wwpLeosCfmExtDelaySessionEntry 20 }
     
  wwpLeosCfmExtDelaySessionMinJitter OBJECT-TYPE
 	 SYNTAX			Unsigned32
 	 MAX-ACCESS		read-only
 	 STATUS			current 
     DESCRIPTION	
    	     "This object specifies the minimum jitter(microseconds) seen on DMR frames received
	     during the last iteration of the completed test."
     ::= { wwpLeosCfmExtDelaySessionEntry 21 }
     
  wwpLeosCfmExtDelaySessionAvgJitter OBJECT-TYPE
 	 SYNTAX			Unsigned32
 	 MAX-ACCESS		read-only
 	 STATUS			current 
     DESCRIPTION	
    	     "This object specifies the average jitter(microseconds) seen on DMR frames during the 
	     last iteration of the completed test."
     ::= { wwpLeosCfmExtDelaySessionEntry 22 }          
     
  wwpLeosCfmExtDelaySessionMaxJitter OBJECT-TYPE
 	 SYNTAX			Unsigned32
 	MAX-ACCESS		read-only
 	STATUS			current 
    DESCRIPTION	
    	"This object specifies the maximum jitter(microseconds) seen on DMR frames during
	the last iteration of the completed test."
    ::= { wwpLeosCfmExtDelaySessionEntry 23 }

  wwpLeosCfmExtDelaySessionDelayCounterBin0 OBJECT-TYPE
         SYNTAX                 Unsigned32
         MAX-ACCESS             read-only
         STATUS                 current
     DESCRIPTION
             "This object counters the number of frame delay measurements whose measured delay falls into a threshold range Bin 1."
     ::= { wwpLeosCfmExtDelaySessionEntry 24 }

  wwpLeosCfmExtDelaySessionDelayCounterBin1 OBJECT-TYPE
         SYNTAX                 Unsigned32
         MAX-ACCESS             read-only
         STATUS                 current
     DESCRIPTION
             "This object counters the number of frame delay measurements whose measured delay falls into a threshold range Bin 1."
     ::= { wwpLeosCfmExtDelaySessionEntry 25 }

  wwpLeosCfmExtDelaySessionDelayCounterBin2 OBJECT-TYPE
         SYNTAX                 Unsigned32
         MAX-ACCESS             read-only
         STATUS                 current
     DESCRIPTION
             "This object counters the number of frame delay measurements whose measured delay falls into a threshold range Bin 2."
     ::= { wwpLeosCfmExtDelaySessionEntry 26 }

  wwpLeosCfmExtDelaySessionDelayCounterBin3 OBJECT-TYPE
         SYNTAX                 Unsigned32
         MAX-ACCESS             read-only
         STATUS                 current
     DESCRIPTION
             "This object counters the number of frame delay measurements whose measured delay falls into a threshold range Bin 3."
     ::= { wwpLeosCfmExtDelaySessionEntry 27 }

  wwpLeosCfmExtDelaySessionDelayCounterBin4 OBJECT-TYPE
         SYNTAX                 Unsigned32
         MAX-ACCESS             read-only
         STATUS                 current
     DESCRIPTION
             "This object counters the number of frame delay measurements whose measured delay falls into a threshold range Bin 4."
     ::= { wwpLeosCfmExtDelaySessionEntry 28 }

  wwpLeosCfmExtDelaySessionDelayCounterBin5 OBJECT-TYPE
         SYNTAX                 Unsigned32
         MAX-ACCESS             read-only
         STATUS                 current
     DESCRIPTION
             "This object counters the number of frame delay measurements whose measured delay falls into a threshold range Bin 5."
     ::= { wwpLeosCfmExtDelaySessionEntry 29 }

  wwpLeosCfmExtDelaySessionDelayCounterBin6 OBJECT-TYPE
         SYNTAX                 Unsigned32
         MAX-ACCESS             read-only
         STATUS                 current
     DESCRIPTION
             "This object counters the number of frame delay measurements whose measured delay falls into a threshold range Bin 6."
     ::= { wwpLeosCfmExtDelaySessionEntry 30 }

  wwpLeosCfmExtDelaySessionDelayCounterBin7 OBJECT-TYPE
         SYNTAX                 Unsigned32
         MAX-ACCESS             read-only
         STATUS                 current
     DESCRIPTION
             "This object counters the number of frame delay measurements whose measured delay falls into a threshold range Bin 7."
     ::= { wwpLeosCfmExtDelaySessionEntry 31 }

  wwpLeosCfmExtDelaySessionDelayCounterBin8 OBJECT-TYPE
         SYNTAX                 Unsigned32
         MAX-ACCESS             read-only
         STATUS                 current
     DESCRIPTION
             "This object counters the number of frame delay measurements whose measured delay falls into a threshold range Bin 8."
     ::= { wwpLeosCfmExtDelaySessionEntry 32 }

  wwpLeosCfmExtDelaySessionDelayCounterBin9 OBJECT-TYPE
         SYNTAX                 Unsigned32
         MAX-ACCESS             read-only
         STATUS                 current
     DESCRIPTION
             "This object counters the number of frame delay measurements whose measured delay falls into a threshold range Bin 9."
     ::= { wwpLeosCfmExtDelaySessionEntry 33 }

  wwpLeosCfmExtDelaySessionDelayCounterBin10 OBJECT-TYPE
         SYNTAX                 Unsigned32
         MAX-ACCESS             read-only
         STATUS                 current
     DESCRIPTION
             "This object counters the number of frame delay measurements whose measured delay falls into a threshold range Bin 10."
     ::= { wwpLeosCfmExtDelaySessionEntry 34 }

  wwpLeosCfmExtDelaySessionJitterCounterBin0 OBJECT-TYPE
         SYNTAX                 Unsigned32
         MAX-ACCESS             read-only
         STATUS                 current
     DESCRIPTION
             "This object counters the number of frame delay measurements whose measured jitter falls into a threshold range Bin 1."
     ::= { wwpLeosCfmExtDelaySessionEntry 35 }

  wwpLeosCfmExtDelaySessionJitterCounterBin1 OBJECT-TYPE
         SYNTAX                 Unsigned32
         MAX-ACCESS             read-only
         STATUS                 current
     DESCRIPTION
             "This object counters the number of frame delay measurements whose measured jitter falls into a threshold range Bin 1."
     ::= { wwpLeosCfmExtDelaySessionEntry 36 }

  wwpLeosCfmExtDelaySessionJitterCounterBin2 OBJECT-TYPE
         SYNTAX                 Unsigned32
         MAX-ACCESS             read-only
         STATUS                 current
     DESCRIPTION
             "This object counters the number of frame delay measurements whose measured jitter falls into a threshold range Bin 2."
     ::= { wwpLeosCfmExtDelaySessionEntry 37 }

  wwpLeosCfmExtDelaySessionJitterCounterBin3 OBJECT-TYPE
         SYNTAX                 Unsigned32
         MAX-ACCESS             read-only
         STATUS                 current
     DESCRIPTION
             "This object counters the number of frame delay measurements whose measured jitter falls into a threshold range Bin 3."
     ::= { wwpLeosCfmExtDelaySessionEntry 38 }

  wwpLeosCfmExtDelaySessionJitterCounterBin4 OBJECT-TYPE
         SYNTAX                 Unsigned32
         MAX-ACCESS             read-only
         STATUS                 current
     DESCRIPTION
             "This object counters the number of frame delay measurements whose measured jitter falls into a threshold range Bin 4."
     ::= { wwpLeosCfmExtDelaySessionEntry 39 }

  wwpLeosCfmExtDelaySessionJitterCounterBin5 OBJECT-TYPE
         SYNTAX                 Unsigned32
         MAX-ACCESS             read-only
         STATUS                 current
     DESCRIPTION
             "This object counters the number of frame delay measurements whose measured jitter falls into a threshold range Bin 5."
     ::= { wwpLeosCfmExtDelaySessionEntry 40 }

  wwpLeosCfmExtDelaySessionJitterCounterBin6 OBJECT-TYPE
         SYNTAX                 Unsigned32
         MAX-ACCESS             read-only
         STATUS                 current
     DESCRIPTION
             "This object counters the number of frame delay measurements whose measured jitter falls into a threshold range Bin 6."
     ::= { wwpLeosCfmExtDelaySessionEntry 41 }

  wwpLeosCfmExtDelaySessionJitterCounterBin7 OBJECT-TYPE
         SYNTAX                 Unsigned32
         MAX-ACCESS             read-only
         STATUS                 current
     DESCRIPTION
             "This object counters the number of frame delay measurements whose measured jitter falls into a threshold range Bin 7."
     ::= { wwpLeosCfmExtDelaySessionEntry 42 }

  wwpLeosCfmExtDelaySessionJitterCounterBin8 OBJECT-TYPE
         SYNTAX                 Unsigned32
         MAX-ACCESS             read-only
         STATUS                 current
     DESCRIPTION
             "This object counters the number of frame delay measurements whose measured jitter falls into a threshold range Bin 8."
     ::= { wwpLeosCfmExtDelaySessionEntry 43 }

  wwpLeosCfmExtDelaySessionJitterCounterBin9 OBJECT-TYPE
         SYNTAX                 Unsigned32
         MAX-ACCESS             read-only
         STATUS                 current
     DESCRIPTION
             "This object counters the number of frame delay measurements whose measured jitter falls into a threshold range Bin 9."
     ::= { wwpLeosCfmExtDelaySessionEntry 44 }

  wwpLeosCfmExtDelaySessionJitterCounterBin10 OBJECT-TYPE
         SYNTAX                 Unsigned32
         MAX-ACCESS             read-only
         STATUS                 current
     DESCRIPTION
             "This object counters the number of frame delay measurements whose measured jitter falls into a threshold range Bin 10."
     ::= { wwpLeosCfmExtDelaySessionEntry 45 }

  wwpLeosCfmExtDelaySessionConfigAccelerated	OBJECT-TYPE
 	 SYNTAX			TruthValue
 	 MAX-ACCESS		read-only
 	 STATUS			current
 	 DESCRIPTION
 	     "This object returns true if the measurement session is configured as a hardware accelerated." 
     ::= { wwpLeosCfmExtDelaySessionEntry 46 }   
 	
 wwpLeosCfmExtDelaySessionDelayProfile OBJECT-TYPE
        SYNTAX                  Unsigned32 (1..4096)
        MAX-ACCESS              read-create
        STATUS                  current
        DESCRIPTION
                        "The delay profile index."
     ::= { wwpLeosCfmExtDelaySessionEntry 47 }
 wwpLeosCfmExtDelaySessionJitterProfile OBJECT-TYPE
        SYNTAX                  Unsigned32 (1..4096)
        MAX-ACCESS              read-create
        STATUS                  current
        DESCRIPTION
                        "The jitter profile index."
      ::= { wwpLeosCfmExtDelaySessionEntry 48 }

  wwpLeosCfmExtDelaySessionTotalJitter OBJECT-TYPE
         SYNTAX                 Counter64
         MAX-ACCESS             read-only
         STATUS                 current
         DESCRIPTION
                        "This object specifies the total jitter(microseconds) seen on DMR frames received
                         during the last iteration of the completed test."
      ::= { wwpLeosCfmExtDelaySessionEntry 49 }

  wwpLeosCfmExtDelaySessionForwardMinJitter OBJECT-TYPE
         SYNTAX                 Unsigned32
         MAX-ACCESS             read-only
         STATUS                 current
         DESCRIPTION
                        "This object specifies the minimum jitter(microseconds) seen on DMR frames received
                         during the last iteration of the completed test in forward direction."
      ::= { wwpLeosCfmExtDelaySessionEntry 50 }

  wwpLeosCfmExtDelaySessionForwardMaxJitter OBJECT-TYPE
         SYNTAX                 Unsigned32
         MAX-ACCESS             read-only
         STATUS                 current
         DESCRIPTION
                        "This object specifies the maximum jitter(microseconds) seen on DMR frames during
                         the last iteration of the completed test in forward direction."
      ::= { wwpLeosCfmExtDelaySessionEntry 51 }

  wwpLeosCfmExtDelaySessionForwardAvgJitter OBJECT-TYPE
         SYNTAX                 Unsigned32
         MAX-ACCESS             read-only
         STATUS                 current
         DESCRIPTION
                        "This object specifies the average jitter(microseconds) seen on DMR frames during the 
                         last iteration of the completed test in forward direction."
      ::= { wwpLeosCfmExtDelaySessionEntry 52 }          

  wwpLeosCfmExtDelaySessionForwardTotalJitter OBJECT-TYPE
         SYNTAX                 Counter64
         MAX-ACCESS             read-only
         STATUS                 current
         DESCRIPTION
                        "This object specifies the total jitter(microseconds) seen on DMR frames during the 
                         last iteration of the completed test in forward direction."
      ::= { wwpLeosCfmExtDelaySessionEntry 53 }          

  wwpLeosCfmExtDelaySessionBackwardMinJitter OBJECT-TYPE
         SYNTAX                 Unsigned32
         MAX-ACCESS             read-only
         STATUS                 current
         DESCRIPTION
                        "This object specifies the minimum jitter(microseconds) seen on DMR frames received
                         during the last iteration of the completed test in backward direction."
      ::= { wwpLeosCfmExtDelaySessionEntry 54 }

  wwpLeosCfmExtDelaySessionBackwardMaxJitter OBJECT-TYPE
         SYNTAX                 Unsigned32
         MAX-ACCESS             read-only
         STATUS                 current
         DESCRIPTION
                        "This object specifies the maximum jitter(microseconds) seen on DMR frames during
                         the last iteration of the completed test in backward direction."
      ::= { wwpLeosCfmExtDelaySessionEntry 55 }

  wwpLeosCfmExtDelaySessionBackwardAvgJitter OBJECT-TYPE
         SYNTAX                 Unsigned32
         MAX-ACCESS             read-only
         STATUS                 current
         DESCRIPTION
                        "This object specifies the average jitter(microseconds) seen on DMR frames during the 
                         last iteration of the completed test in backward direction."
      ::= { wwpLeosCfmExtDelaySessionEntry 56 }          
     
  wwpLeosCfmExtDelaySessionBackwardTotalJitter OBJECT-TYPE
         SYNTAX                 Counter64
         MAX-ACCESS             read-only
         STATUS                 current
         DESCRIPTION
                        "This object specifies the total jitter(microseconds) seen on DMR frames during the 
                         last iteration of the completed test in backward direction."
      ::= { wwpLeosCfmExtDelaySessionEntry 57 }          

  wwpLeosCfmExtDelaySessionForwardJitterCounterBin0 OBJECT-TYPE
         SYNTAX                 Unsigned32
         MAX-ACCESS             read-only
         STATUS                 current
         DESCRIPTION
                        "This object counts the number of frame delay measurements in forward direction whose 
                         measured jitter falls into a threshold range Bin 0."
      ::= { wwpLeosCfmExtDelaySessionEntry 58 }

  wwpLeosCfmExtDelaySessionForwardJitterCounterBin1 OBJECT-TYPE
         SYNTAX                 Unsigned32
         MAX-ACCESS             read-only
         STATUS                 current
         DESCRIPTION
                        "This object counts the number of frame delay measurements in forward direction whose 
                         measured jitter falls into a threshold range Bin 1."
      ::= { wwpLeosCfmExtDelaySessionEntry 59 }

  wwpLeosCfmExtDelaySessionForwardJitterCounterBin2 OBJECT-TYPE
         SYNTAX                 Unsigned32
         MAX-ACCESS             read-only
         STATUS                 current
         DESCRIPTION
                        "This object counts the number of frame delay measurements in forward direction whose
                         measured jitter falls into a threshold range Bin 2."
      ::= { wwpLeosCfmExtDelaySessionEntry 60 }

  wwpLeosCfmExtDelaySessionForwardJitterCounterBin3 OBJECT-TYPE
         SYNTAX                 Unsigned32
         MAX-ACCESS             read-only
         STATUS                 current
         DESCRIPTION
                        "This object counts the number of frame delay measurements in forward direction whose 
                         measured jitter falls into a threshold range Bin 3."
      ::= { wwpLeosCfmExtDelaySessionEntry 61 }

  wwpLeosCfmExtDelaySessionForwardJitterCounterBin4 OBJECT-TYPE
         SYNTAX                 Unsigned32
         MAX-ACCESS             read-only
         STATUS                 current
         DESCRIPTION
                        "This object counts the number of frame delay measurements in forward direction whose 
                         measured jitter falls into a threshold range Bin 4."
      ::= { wwpLeosCfmExtDelaySessionEntry 62 }

  wwpLeosCfmExtDelaySessionForwardJitterCounterBin5 OBJECT-TYPE
         SYNTAX                 Unsigned32
         MAX-ACCESS             read-only
         STATUS                 current
         DESCRIPTION
                        "This object counts the number of frame delay measurements in forward direction whose 
                         measured jitter falls into a threshold range Bin 5."
      ::= { wwpLeosCfmExtDelaySessionEntry 63 }

  wwpLeosCfmExtDelaySessionForwardJitterCounterBin6 OBJECT-TYPE
         SYNTAX                 Unsigned32
         MAX-ACCESS             read-only
         STATUS                 current
         DESCRIPTION
                        "This object counts the number of frame delay measurements in forward direction whose 
                         measured jitter falls into a threshold range Bin 6."
      ::= { wwpLeosCfmExtDelaySessionEntry 64 }

  wwpLeosCfmExtDelaySessionForwardJitterCounterBin7 OBJECT-TYPE
         SYNTAX                 Unsigned32
         MAX-ACCESS             read-only
         STATUS                 current
         DESCRIPTION
                        "This object counts the number of frame delay measurements in forward direction whose 
                         measured jitter falls into a threshold range Bin 7."
      ::= { wwpLeosCfmExtDelaySessionEntry 65 }

  wwpLeosCfmExtDelaySessionForwardJitterCounterBin8 OBJECT-TYPE
         SYNTAX                 Unsigned32
         MAX-ACCESS             read-only
         STATUS                 current
         DESCRIPTION
                        "This object counts the number of frame delay measurements in forward direction whose 
                         measured jitter falls into a threshold range Bin 8."
      ::= { wwpLeosCfmExtDelaySessionEntry 66 }

  wwpLeosCfmExtDelaySessionForwardJitterCounterBin9 OBJECT-TYPE
         SYNTAX                 Unsigned32
         MAX-ACCESS             read-only
         STATUS                 current
         DESCRIPTION
                        "This object counts the number of frame delay measurements in forward direction whose 
                         measured jitter falls into a threshold range Bin 9."
      ::= { wwpLeosCfmExtDelaySessionEntry 67 }

  wwpLeosCfmExtDelaySessionForwardJitterCounterBin10 OBJECT-TYPE
         SYNTAX                 Unsigned32
         MAX-ACCESS             read-only
         STATUS                 current
         DESCRIPTION
                        "This object counts the number of frame delay measurements in forward direction whose 
                         measured jitter falls into a threshold range Bin 10."
      ::= { wwpLeosCfmExtDelaySessionEntry 68 }

   wwpLeosCfmExtDelaySessionBackwardJitterCounterBin0 OBJECT-TYPE
         SYNTAX                 Unsigned32
         MAX-ACCESS             read-only
         STATUS                 current
         DESCRIPTION
                        "This object counts the number of frame delay measurements in backward direction whose 
                         measured jitter falls into a threshold range Bin 0."
      ::= { wwpLeosCfmExtDelaySessionEntry 69 }

  wwpLeosCfmExtDelaySessionBackwardJitterCounterBin1 OBJECT-TYPE
         SYNTAX                 Unsigned32
         MAX-ACCESS             read-only
         STATUS                 current
         DESCRIPTION
                        "This object counts the number of frame delay measurements in backward direction whose 
                         measured jitter falls into a threshold range Bin 1."
      ::= { wwpLeosCfmExtDelaySessionEntry 70 }

  wwpLeosCfmExtDelaySessionBackwardJitterCounterBin2 OBJECT-TYPE
         SYNTAX                 Unsigned32
         MAX-ACCESS             read-only
         STATUS                 current
         DESCRIPTION
                        "This object counts the number of frame delay measurements in backward direction whose 
                         measured jitter falls into a threshold range Bin 2."
      ::= { wwpLeosCfmExtDelaySessionEntry 71 }

  wwpLeosCfmExtDelaySessionBackwardJitterCounterBin3 OBJECT-TYPE
         SYNTAX                 Unsigned32
         MAX-ACCESS             read-only
         STATUS                 current
         DESCRIPTION
                        "This object counts the number of frame delay measurements in backward direction whose 
                         measured jitter falls into a threshold range Bin 3."
      ::= { wwpLeosCfmExtDelaySessionEntry 72 }

  wwpLeosCfmExtDelaySessionBackwardJitterCounterBin4 OBJECT-TYPE
         SYNTAX                 Unsigned32
         MAX-ACCESS             read-only
         STATUS                 current
         DESCRIPTION
                        "This object counts the number of frame delay measurements in backward direction whose 
                         measured jitter falls into a threshold range Bin 4."
      ::= { wwpLeosCfmExtDelaySessionEntry 73 }

  wwpLeosCfmExtDelaySessionBackwardJitterCounterBin5 OBJECT-TYPE
         SYNTAX                 Unsigned32
         MAX-ACCESS             read-only
         STATUS                 current
         DESCRIPTION
                        "This object counts the number of frame delay measurements in backward direction whose 
                         measured jitter falls into a threshold range Bin 5."
      ::= { wwpLeosCfmExtDelaySessionEntry 74 }

  wwpLeosCfmExtDelaySessionBackwardJitterCounterBin6 OBJECT-TYPE
         SYNTAX                 Unsigned32
         MAX-ACCESS             read-only
         STATUS                 current
         DESCRIPTION
                        "This object counts the number of frame delay measurements in backward direction whose 
                         measured jitter falls into a threshold range Bin 6."
      ::= { wwpLeosCfmExtDelaySessionEntry 75 }

  wwpLeosCfmExtDelaySessionBackwardJitterCounterBin7 OBJECT-TYPE
         SYNTAX                 Unsigned32
         MAX-ACCESS             read-only
         STATUS                 current
         DESCRIPTION
                        "This object counts the number of frame delay measurements in backward direction whose 
                         measured jitter falls into a threshold range Bin 7."
      ::= { wwpLeosCfmExtDelaySessionEntry 76 }

  wwpLeosCfmExtDelaySessionBackwardJitterCounterBin8 OBJECT-TYPE
         SYNTAX                 Unsigned32
         MAX-ACCESS             read-only
         STATUS                 current
         DESCRIPTION
                        "This object counts the number of frame delay measurements in backward direction whose 
                         measured jitter falls into a threshold range Bin 8."
      ::= { wwpLeosCfmExtDelaySessionEntry 77 }

  wwpLeosCfmExtDelaySessionBackwardJitterCounterBin9 OBJECT-TYPE
         SYNTAX                 Unsigned32
         MAX-ACCESS             read-only
         STATUS                 current
         DESCRIPTION
                        "This object counts the number of frame delay measurements in backward direction whose 
                         measured jitter falls into a threshold range Bin 9."
      ::= { wwpLeosCfmExtDelaySessionEntry 78 }

  wwpLeosCfmExtDelaySessionBackwardJitterCounterBin10 OBJECT-TYPE
         SYNTAX                 Unsigned32
         MAX-ACCESS             read-only
         STATUS                 current
         DESCRIPTION
                        "This object counts the number of frame delay measurements in backward direction whose 
                         measured jitter falls into a threshold range Bin 10."
      ::= { wwpLeosCfmExtDelaySessionEntry 79 }

  wwpLeosCfmExtDelaySessionSuspect OBJECT-TYPE
         SYNTAX                 TruthValue
         MAX-ACCESS             read-only
         STATUS                 current
         DESCRIPTION
                        "This object indicates that there is discontinuity in DMM Performance Measurement.
                         Condition for discontinuity include:
                         a) The conducting of performance measurement is halted before the current measurement 
                            interval is completed."
      ::= { wwpLeosCfmExtDelaySessionEntry 80 }

  wwpLeosCfmExtDelaySessionForwardMinDelay OBJECT-TYPE
         SYNTAX                 Integer32
         MAX-ACCESS             read-only
         STATUS                 current
         DESCRIPTION
                        "This object specifies the minimum delay(microseconds) seen on DMR frames received
                         during the last iteration of the completed test in forward direction."
      ::= { wwpLeosCfmExtDelaySessionEntry 81 }

  wwpLeosCfmExtDelaySessionForwardAveDelay OBJECT-TYPE
         SYNTAX                 Integer32
         MAX-ACCESS             read-only
         STATUS                 current
         DESCRIPTION
                        "This object specifies the minimum delay(microseconds) seen on DMR frames received
                         during the last iteration of the completed test in forward direction."
      ::= { wwpLeosCfmExtDelaySessionEntry 82 }

  wwpLeosCfmExtDelaySessionForwardMaxDelay OBJECT-TYPE
         SYNTAX                 Integer32
         MAX-ACCESS             read-only
         STATUS                 current
         DESCRIPTION
                        "This object specifies the minimum delay(microseconds) seen on DMR frames received
                         during the last iteration of the completed test in forward direction."
      ::= { wwpLeosCfmExtDelaySessionEntry 83 }

  wwpLeosCfmExtDelaySessionBackwardMinDelay OBJECT-TYPE
         SYNTAX                 Integer32
         MAX-ACCESS             read-only
         STATUS                 current
         DESCRIPTION
                        "This object specifies the minimum delay(microseconds) seen on DMR frames received
                         during the last iteration of the completed test in backward direction."
      ::= { wwpLeosCfmExtDelaySessionEntry 84 }

  wwpLeosCfmExtDelaySessionBackwardAveDelay OBJECT-TYPE
         SYNTAX                 Integer32
         MAX-ACCESS             read-only
         STATUS                 current
         DESCRIPTION
                        "This object specifies the minimum delay(microseconds) seen on DMR frames received
                         during the last iteration of the completed test in backward direction."
      ::= { wwpLeosCfmExtDelaySessionEntry 85 }

  wwpLeosCfmExtDelaySessionBackwardMaxDelay OBJECT-TYPE
         SYNTAX                 Integer32
         MAX-ACCESS             read-only
         STATUS                 current
         DESCRIPTION
                        "This object specifies the minimum delay(microseconds) seen on DMR frames received
                         during the last iteration of the completed test in backward direction."
      ::= { wwpLeosCfmExtDelaySessionEntry 86 }

  wwpLeosCfmExtDelaySessionConfigTimestampType OBJECT-TYPE
     SYNTAX       CfmTimestampType
     MAX-ACCESS   read-only
     STATUS       current
     DESCRIPTION
             "This object specifies the timestamp type to be embedded in outgoing DMM and incoming DMR Frames at Delay Initiator."
     DEFVAL       {hardware}
     ::= { wwpLeosCfmExtDelaySessionEntry 87 }

  wwpLeosCfmExtDelaySessionCosMode OBJECT-TYPE
     SYNTAX       TruthValue
     MAX-ACCESS   read-only
     STATUS       current
     DESCRIPTION
             "This object returns true if the cos-mode is specified in the measurement session.
              Cos-mode substitutes DMR p-bits for test-id when TestId TLV is missing."
     ::= { wwpLeosCfmExtDelaySessionEntry 88 }

  wwpLeosCfmExtDelaySessionSdDelayClearThreshold OBJECT-TYPE
     SYNTAX                 Integer32 (-1..2147483646)
     MAX-ACCESS             read-create
     STATUS                 current
     DESCRIPTION
             "This object represents the signal degrade clear threshold value for the delay measurement test.
              A value of 0 or greater is compared to the delay result and a fault is cleared, if average two-way delay
              is equal to or below this threshold after an iteration. A value of -1 disables the generation of signal
              degrade fault notification. This object works in conjunction with wwpLeosCfmExtDelaySessionSdDelaySetThreshold.
              If clear object is given non-default value, set object should be also set to non-default value."
     DEFVAL {-1}
     ::= { wwpLeosCfmExtDelaySessionEntry 89 }

  wwpLeosCfmExtDelaySessionSdDelaySetThreshold OBJECT-TYPE
     SYNTAX                 Integer32 (-1 | 1..2147483647)
     MAX-ACCESS             read-create
     STATUS                 current
     DESCRIPTION
             "This object represents the signal degrade set threshold value for the delay measurement test.
              A value of 1 or greater is compared to the delay result and fault is set, if the average two-delay exceeds
              this threshold after an iteration. A value of -1 disables the generation of signal degrade fault notification.
              This object works in conjunction with wwpLeosCfmExtDelaySessionSdDelayClearThreshold. If set object is given
              non-default value, clear object should be also set to non-default value."
     DEFVAL {-1}
     ::= { wwpLeosCfmExtDelaySessionEntry 90 }

  wwpLeosCfmExtDelaySessionSdJitterClearThreshold OBJECT-TYPE
     SYNTAX                 Integer32 (-1..2147483646)
     MAX-ACCESS             read-create
     STATUS                 current
     DESCRIPTION
             "This object represents the signal degrade clear threshold value for the delay measurement test.
              A value of 0 or greater is compared to the delay result and a fault is cleared, if average backward jitter
              is equal to or below this threshold after an iteration. A value of -1 disables the generation of signal
              degrade fault notification. This object works in conjunction with wwpLeosCfmExtDelaySessionSdJitterSetThreshold.
              If clear object is given non-default value, set object should be also set to non-default value."
     DEFVAL {-1}
     ::= { wwpLeosCfmExtDelaySessionEntry 91 }

  wwpLeosCfmExtDelaySessionSdJitterSetThreshold OBJECT-TYPE
     SYNTAX                 Integer32 (-1 | 1..2147483647)
     MAX-ACCESS             read-create
     STATUS                 current
     DESCRIPTION
             "This object represents the signal degrade set threshold value for the delay measurement test.
              A value of 1 or greater is compared to the delay result and fault is set, if the average backward jitter exceeds
              this threshold after an iteration. A value of -1 disables the generation of signal degrade fault notification.
              This object works in conjunction with wwpLeosCfmExtDelaySessionSdJitterClearThreshold. If set object is given
              non-default value, clear object should be also set to non-default value."
     DEFVAL {-1}
     ::= { wwpLeosCfmExtDelaySessionEntry 92 }

  wwpLeosCfmExtDelaySessionForwardJitterProfile OBJECT-TYPE
     SYNTAX                 Unsigned32 (1..4096)
     MAX-ACCESS             read-create
     STATUS                 current
     DESCRIPTION
             "The jitter profile index for one way dmm forward direction. The default value is 1."
     DEFVAL {1}
     ::= { wwpLeosCfmExtDelaySessionEntry 93 }

  wwpLeosCfmExtDelaySessionBackwardJitterProfile OBJECT-TYPE
     SYNTAX                  Unsigned32 (1..4096)
     MAX-ACCESS              read-create
     STATUS                  current
     DESCRIPTION
             "The jitter profile index for one way dmm backward direction. The default value is 1."
     DEFVAL {1}
     ::= { wwpLeosCfmExtDelaySessionEntry 94 }

 --
 -- DMM history multiple cos
 --
  wwpLeosCfmExtDelaySessionHistoryTable OBJECT-TYPE
     SYNTAX         SEQUENCE OF WwpLeosCfmExtDelaySessionHistoryEntry
     MAX-ACCESS     not-accessible
     STATUS         current
     DESCRIPTION     "The (conceptual) table listing the Y.1731 Delay
                     History table for the CFM MEP."  
     ::= { wwpLeosCfmExtDelay 3}    
     
  wwpLeosCfmExtDelaySessionHistoryEntry OBJECT-TYPE
     SYNTAX          WwpLeosCfmExtDelaySessionHistoryEntry
     MAX-ACCESS      not-accessible
     STATUS          current
     DESCRIPTION    "An entry (conceptual row) in the wwpLeosCfmExtDelaySessionHistoryTable."
     INDEX {wwpLeosCfmServiceIndex, wwpLeosCfmExtMEPId,wwpLeosCfmRemoteMEPID,wwpLeosCfmExtDelaySessionTestId ,
            wwpLeosCfmExtDelaySessionHistoryIndex}
     ::= { wwpLeosCfmExtDelaySessionHistoryTable 1 }   
 
  WwpLeosCfmExtDelaySessionHistoryEntry ::=  SEQUENCE {
     wwpLeosCfmExtDelaySessionHistoryIndex                    Unsigned32,
     wwpLeosCfmExtDelaySessionHistoryServiceName              DisplayString,
     wwpLeosCfmExtDelaySessionHistoryLocalMepid               Unsigned32,
     wwpLeosCfmExtDelaySessionHistoryLocalMacAddr             MacAddress,
     wwpLeosCfmExtDelaySessionHistoryRemoteMEPId              Unsigned32,
     wwpLeosCfmExtDelaySessionHistoryRemoteMacAddr            MacAddress,
     wwpLeosCfmExtDelaySessionHistoryTestId                   Unsigned32,
     wwpLeosCfmExtDelaySessionHistoryAccelerate               TruthValue,
     wwpLeosCfmExtDelaySessionHistoryPriority                 Unsigned32,
     wwpLeosCfmExtDelaySessionHistoryIteration                Unsigned32,
     wwpLeosCfmExtDelaySessionHistoryDMMInterval              Unsigned32,
     wwpLeosCfmExtDelaySessionHistoryFrameSize                Unsigned32,
     wwpLeosCfmExtDelaySessionHistoryNumDMMSent               Unsigned32,
     wwpLeosCfmExtDelaySessionHistoryNumDMRReceived           Unsigned32,
     wwpLeosCfmExtDelaySessionHistoryMinDelay                 Unsigned32,
     wwpLeosCfmExtDelaySessionHistoryAveDelay                 Unsigned32,
     wwpLeosCfmExtDelaySessionHistoryMaxDelay                 Unsigned32,
     wwpLeosCfmExtDelaySessionHistoryMinJitter                Unsigned32,
     wwpLeosCfmExtDelaySessionHistoryAveJitter                Unsigned32,
     wwpLeosCfmExtDelaySessionHistoryMaxJitter                Unsigned32,
     wwpLeosCfmExtDelaySessionHistoryStartTime                Unsigned32,
     wwpLeosCfmExtDelaySessionHistoryStopTime                 Unsigned32,
     wwpLeosCfmExtDelaySessionHistoryDuration                 Unsigned32,
     wwpLeosCfmExtDelaySessionHistoryStatus                   INTEGER,
     wwpLeosCfmExtDelaySessionHistoryClear                    INTEGER,
     wwpLeosCfmExtDelaySessionHistoryTotalJitter              Counter64,
     wwpLeosCfmExtDelaySessionHistoryForwardMinJitter         Unsigned32,
     wwpLeosCfmExtDelaySessionHistoryForwardAveJitter         Unsigned32,
     wwpLeosCfmExtDelaySessionHistoryForwardMaxJitter         Unsigned32,
     wwpLeosCfmExtDelaySessionHistoryForwardTotalJitter       Counter64, 
     wwpLeosCfmExtDelaySessionHistoryBackwardMinJitter        Unsigned32,
     wwpLeosCfmExtDelaySessionHistoryBackwardAveJitter        Unsigned32,
     wwpLeosCfmExtDelaySessionHistoryBackwardMaxJitter        Unsigned32,
     wwpLeosCfmExtDelaySessionHistoryBackwardTotalJitter      Counter64, 
     wwpLeosCfmExtDelaySessionHistorySuspect                  TruthValue,
     wwpLeosCfmExtDelaySessionHistoryForwardMinDelay          Integer32,
     wwpLeosCfmExtDelaySessionHistoryForwardAveDelay          Integer32,
     wwpLeosCfmExtDelaySessionHistoryForwardMaxDelay          Integer32,
     wwpLeosCfmExtDelaySessionHistoryBackwardMinDelay         Integer32,
     wwpLeosCfmExtDelaySessionHistoryBackwardAveDelay         Integer32,
     wwpLeosCfmExtDelaySessionHistoryBackwardMaxDelay         Integer32,
     wwpLeosCfmExtDelaySessionHistorySignalDegradeStatus      TruthValue,
     wwpLeosCfmExtDelaySessionHistorySignalDegradeSuspect     TruthValue
  }
  
  wwpLeosCfmExtDelaySessionHistoryIndex OBJECT-TYPE
     SYNTAX      	Unsigned32 (1..256)
     MAX-ACCESS  	not-accessible
     STATUS      	current
     DESCRIPTION		"This is the history entry index into the table."
     ::= { wwpLeosCfmExtDelaySessionHistoryEntry 1 }
     	
  wwpLeosCfmExtDelaySessionHistoryServiceName OBJECT-TYPE
     SYNTAX       DisplayString (SIZE(1..45))
     MAX-ACCESS   read-only
     STATUS       current
     DESCRIPTION
             "This object identifies the CFM service name."
     ::= { wwpLeosCfmExtDelaySessionHistoryEntry 2 }  
      
  wwpLeosCfmExtDelaySessionHistoryLocalMepid OBJECT-TYPE
     SYNTAX      Unsigned32
     MAX-ACCESS  read-only
     STATUS      current
     DESCRIPTION
             "This object identifies the local mepid."
     ::= { wwpLeosCfmExtDelaySessionHistoryEntry 3 } 
     
  wwpLeosCfmExtDelaySessionHistoryLocalMacAddr OBJECT-TYPE
     SYNTAX      MacAddress
     MAX-ACCESS  read-only
     STATUS      current
     DESCRIPTION
             "This object identifies the MAC address of the local mep. "
     ::= { wwpLeosCfmExtDelaySessionHistoryEntry 4 }  
     
  wwpLeosCfmExtDelaySessionHistoryRemoteMEPId OBJECT-TYPE
     SYNTAX      	Unsigned32 
     MAX-ACCESS  	read-only
     STATUS      	current
     DESCRIPTION    
             "This object identifies the remote mepid this test is run against."
     ::= { wwpLeosCfmExtDelaySessionHistoryEntry 5 }   
    
  wwpLeosCfmExtDelaySessionHistoryRemoteMacAddr OBJECT-TYPE
     SYNTAX      MacAddress
     MAX-ACCESS  read-only
     STATUS      current
     DESCRIPTION
             "This object identifies the MAC address of the remote mep."
     ::= { wwpLeosCfmExtDelaySessionHistoryEntry 6 }  
     
  wwpLeosCfmExtDelaySessionHistoryTestId OBJECT-TYPE
     SYNTAX       Unsigned32
     MAX-ACCESS   read-only
     STATUS       current
     DESCRIPTION
             "This object specifies the DMM test id to be
              used when sending link DMM."
     ::= { wwpLeosCfmExtDelaySessionHistoryEntry 7 }
  
   wwpLeosCfmExtDelaySessionHistoryAccelerate OBJECT-TYPE
     SYNTAX       TruthValue
     MAX-ACCESS   read-only
     STATUS       current
     DESCRIPTION
             "This object specifies if the test session was accelerated
             or not."
     ::= { wwpLeosCfmExtDelaySessionHistoryEntry 8 }
   
  wwpLeosCfmExtDelaySessionHistoryPriority OBJECT-TYPE
    SYNTAX      	Unsigned32 
    MAX-ACCESS  	read-only
    STATUS      	current
    DESCRIPTION
            "This object identifies the message priority of the Y.1731 DMM Frames sent on the given DMM test."  
    ::= { wwpLeosCfmExtDelaySessionHistoryEntry 9 }  
    
  wwpLeosCfmExtDelaySessionHistoryIteration  OBJECT-TYPE  
     SYNTAX       Unsigned32 
     MAX-ACCESS   read-only
     STATUS       current
     DESCRIPTION
             "This object indicates the iteration number of this session."
     ::= { wwpLeosCfmExtDelaySessionHistoryEntry 10 }
       
  wwpLeosCfmExtDelaySessionHistoryDMMInterval OBJECT-TYPE
     SYNTAX      	Unsigned32
     MAX-ACCESS  	read-only
     STATUS      	current
     DESCRIPTION  
             "This object identifies the DMM interval used to transmit the Y.1731 DMM Frames sent in this test."  
     ::= { wwpLeosCfmExtDelaySessionHistoryEntry 11 } 
     
  wwpLeosCfmExtDelaySessionHistoryFrameSize OBJECT-TYPE
     SYNTAX      	Unsigned32
     MAX-ACCESS  	read-only
     STATUS      	current
     DESCRIPTION  
             "This object identifies the DMM interval used to transmit the Y.1731 DMM Frames sent in this test."  
     ::= { wwpLeosCfmExtDelaySessionHistoryEntry 12 }
     
  wwpLeosCfmExtDelaySessionHistoryNumDMMSent OBJECT-TYPE
 	 SYNTAX			Unsigned32
 	 MAX-ACCESS		read-only
 	 STATUS			current 
     DESCRIPTION	
    	     "This object specifies the number of DMM frames sent during the test iteration."
     ::= { wwpLeosCfmExtDelaySessionHistoryEntry 13 }   
    
  wwpLeosCfmExtDelaySessionHistoryNumDMRReceived OBJECT-TYPE
 	 SYNTAX			Unsigned32
 	 MAX-ACCESS		read-only
 	 STATUS			current 
     DESCRIPTION	
    	     "This object specifies the number of DMR frames received during the test iteration."
     ::= { wwpLeosCfmExtDelaySessionHistoryEntry 14 } 
    
  wwpLeosCfmExtDelaySessionHistoryMinDelay OBJECT-TYPE
 	 SYNTAX			Unsigned32
 	 MAX-ACCESS		read-only
 	 STATUS			current 
     DESCRIPTION	
    	     "This object specifies the minimum delay(microseconds) seen on DMR frames received in the test iteration."
     ::= { wwpLeosCfmExtDelaySessionHistoryEntry 15 }  
    
  wwpLeosCfmExtDelaySessionHistoryAveDelay OBJECT-TYPE
 	 SYNTAX			Unsigned32
 	 MAX-ACCESS		read-only
 	 STATUS			current 
     DESCRIPTION	
    	     "This object specifies the average delay(microseconds) seen on DMR frames received in the test iteration."
     ::= { wwpLeosCfmExtDelaySessionHistoryEntry 16 } 
    
  wwpLeosCfmExtDelaySessionHistoryMaxDelay OBJECT-TYPE
 	 SYNTAX			Unsigned32
 	 MAX-ACCESS		read-only
 	 STATUS			current 
     DESCRIPTION	
    	     "This object specifies the maximum delay(microseconds) seen on DMR frames received in the test iteration."
     ::= { wwpLeosCfmExtDelaySessionHistoryEntry 17 } 
    
  wwpLeosCfmExtDelaySessionHistoryMinJitter OBJECT-TYPE
 	 SYNTAX			Unsigned32
 	 MAX-ACCESS		read-only
 	 STATUS			current 
     DESCRIPTION	
    	     "This object specifies the minimum jitter(microseconds) seen on DMR frames received in the test iteration."
     ::= { wwpLeosCfmExtDelaySessionHistoryEntry 18 }
    
  wwpLeosCfmExtDelaySessionHistoryAveJitter OBJECT-TYPE
 	 SYNTAX			Unsigned32
 	 MAX-ACCESS		read-only
 	 STATUS			current 
     DESCRIPTION	
    	     "This object specifies the average jitter(microseconds) seen on DMR frames in the test iteration."
     ::= { wwpLeosCfmExtDelaySessionHistoryEntry 19 }  
    
  wwpLeosCfmExtDelaySessionHistoryMaxJitter OBJECT-TYPE
 	 SYNTAX			Unsigned32
 	 MAX-ACCESS		read-only
 	 STATUS			current 
     DESCRIPTION	
    	     "This object specifies the maximum jitter(microseconds) seen on DMR frames in the test iteration."
     ::= { wwpLeosCfmExtDelaySessionHistoryEntry 20 } 
    
  wwpLeosCfmExtDelaySessionHistoryStartTime OBJECT-TYPE
 	 SYNTAX			Unsigned32
 	 MAX-ACCESS		read-only
 	 STATUS			current
 	 DESCRIPTION	
 	    "The time the test iteration started .The timestamp is the number of seconds since 12AM Jan 1st, 1970."
 	 ::= { wwpLeosCfmExtDelaySessionHistoryEntry 21 }  
 	
  wwpLeosCfmExtDelaySessionHistoryStopTime OBJECT-TYPE
 	 SYNTAX			Unsigned32
 	 MAX-ACCESS		read-only
 	 STATUS			current                                   
 	 DESCRIPTION	
 	    "The time the test terminated .The timestamp is the number of seconds since 12AM Jan 1st, 1970."
 	 ::= { wwpLeosCfmExtDelaySessionHistoryEntry 22 }    
 	
  wwpLeosCfmExtDelaySessionHistoryDuration OBJECT-TYPE
 	 SYNTAX			Unsigned32
 	 MAX-ACCESS		read-only
 	 STATUS			current                                   
 	 DESCRIPTION
 	   "The duration of time the test took to complete one iteration."
 	 ::= { wwpLeosCfmExtDelaySessionHistoryEntry 23 }  
 	
  wwpLeosCfmExtDelaySessionHistoryStatus OBJECT-TYPE
     SYNTAX      	INTEGER 
                    {
     					start(1),
     					done(2),
     					canceled(3),
     					timeout(4)
     				}
     MAX-ACCESS  	read-only
     STATUS      	current
     DESCRIPTION     
             "This object specifies the status of the test iteration.
             start - Test iteration transitions to this state once the test is started and in progress.
             done  - Test iteration transitions to this state once the test is completed.    
                     Transition to this state happens only after receiving all the responses and the timeout
                     if any is completed. 
             cancelled - Test iteration transitions to this state if the test was interrupted while it was running.
                         Such an interruption can happen if user explicitly  cancels the test or cfm/service was disabled. 
             timeout - Test session transitions to this state when all the messages were transmitted and has completed with errors. These 
                       errors can occur when the delay timeout has expired and not all responses were received."  
     ::= { wwpLeosCfmExtDelaySessionHistoryEntry 24 }   
    
  wwpLeosCfmExtDelaySessionHistoryClear OBJECT-TYPE
  	 SYNTAX 	    INTEGER
 	                {
 					    none(0),
 						clear(1)
 					}
   	 MAX-ACCESS 		read-write
 	 STATUS 			current
 	 DESCRIPTION 	
 	         "Setting this object to clear(1), clears MEP delay history for the
 		     given service and MepId.  This object cannot be set to none."
 	 ::= { wwpLeosCfmExtDelaySessionHistoryEntry 25 }    

  wwpLeosCfmExtDelaySessionHistoryTotalJitter OBJECT-TYPE
 	 SYNTAX			Counter64
 	 MAX-ACCESS		read-only
 	 STATUS			current 
 	 DESCRIPTION 	
 	         "This object specifies the total jitter(microseconds) seen on DMR frames received in the test iteration."
 	 ::= { wwpLeosCfmExtDelaySessionHistoryEntry 26 }
 
  wwpLeosCfmExtDelaySessionHistoryForwardMinJitter OBJECT-TYPE
 	 SYNTAX			Unsigned32
 	 MAX-ACCESS		read-only
 	 STATUS			current 
 	 DESCRIPTION 	
 	         "This object specifies the minimum jitter(microseconds) seen on DMR frames received in the test iteration in forward direction."
 	 ::= { wwpLeosCfmExtDelaySessionHistoryEntry 27 }
    
  wwpLeosCfmExtDelaySessionHistoryForwardAveJitter OBJECT-TYPE
 	 SYNTAX			Unsigned32
 	 MAX-ACCESS		read-only
 	 STATUS			current 
 	 DESCRIPTION 	
 	         "This object specifies the average jitter(microseconds) seen on DMR frames in the test iteration in forward direction."
 	 ::= { wwpLeosCfmExtDelaySessionHistoryEntry 28 }  
    
  wwpLeosCfmExtDelaySessionHistoryForwardMaxJitter OBJECT-TYPE
 	 SYNTAX			Unsigned32
 	 MAX-ACCESS		read-only
 	 STATUS			current 
 	 DESCRIPTION 	
 	         "This object specifies the maximum jitter(microseconds) seen on DMR frames in the test iteration in forward direction."
 	 ::= { wwpLeosCfmExtDelaySessionHistoryEntry 29 } 

   wwpLeosCfmExtDelaySessionHistoryForwardTotalJitter OBJECT-TYPE
 	 SYNTAX			Counter64
 	 MAX-ACCESS		read-only
 	 STATUS			current 
 	 DESCRIPTION 	
 	         "This object specifies the total jitter(microseconds) seen on DMR frames received in the test iteration in forward direction."
 	 ::= { wwpLeosCfmExtDelaySessionHistoryEntry 30 }

   wwpLeosCfmExtDelaySessionHistoryBackwardMinJitter OBJECT-TYPE
 	 SYNTAX			Unsigned32
 	 MAX-ACCESS		read-only
 	 STATUS			current 
 	 DESCRIPTION 	
 	         "This object specifies the minimum jitter(microseconds) seen on DMR frames received in the test iteration in backward direction."
 	 ::= { wwpLeosCfmExtDelaySessionHistoryEntry 31 }
    
  wwpLeosCfmExtDelaySessionHistoryBackwardAveJitter OBJECT-TYPE
 	 SYNTAX			Unsigned32
 	 MAX-ACCESS		read-only
 	 STATUS			current 
 	 DESCRIPTION 	
 	         "This object specifies the average jitter(microseconds) seen on DMR frames in the test iteration in backward direction."
 	 ::= { wwpLeosCfmExtDelaySessionHistoryEntry 32 }  
    
  wwpLeosCfmExtDelaySessionHistoryBackwardMaxJitter OBJECT-TYPE
 	 SYNTAX			Unsigned32
 	 MAX-ACCESS		read-only
 	 STATUS			current 
 	 DESCRIPTION 	
 	         "This object specifies the maximum jitter(microseconds) seen on DMR frames in the test iteration in backward direction."
 	 ::= { wwpLeosCfmExtDelaySessionHistoryEntry 33 } 

   wwpLeosCfmExtDelaySessionHistoryBackwardTotalJitter OBJECT-TYPE
 	 SYNTAX			Counter64
 	 MAX-ACCESS		read-only
 	 STATUS			current 
 	 DESCRIPTION 	
 	         "This object specifies the total jitter(microseconds) seen on DMR frames received in the test iteration in backward direction."
 	 ::= { wwpLeosCfmExtDelaySessionHistoryEntry 34 }

   wwpLeosCfmExtDelaySessionHistorySuspect OBJECT-TYPE
 	 SYNTAX			TruthValue
 	 MAX-ACCESS		read-only
 	 STATUS			current 
 	 DESCRIPTION 	
 	         "This object indicates that there was discontinuity in DMM Performance Measurement.
 	          Condition for discontinuity include:
 	          a) The conducting of performance measurement is halted before the current measurement interval is completed."
 	 ::= { wwpLeosCfmExtDelaySessionHistoryEntry 35 }

  wwpLeosCfmExtDelaySessionHistoryForwardMinDelay OBJECT-TYPE
 	 SYNTAX			Integer32
 	 MAX-ACCESS		read-only
 	 STATUS			current 
 	 DESCRIPTION 	
 	         "This object specifies the minimum delay(microseconds) seen on DMR frames received in the test iteration in forward direction."
 	 ::= { wwpLeosCfmExtDelaySessionHistoryEntry 36 }
    
  wwpLeosCfmExtDelaySessionHistoryForwardAveDelay OBJECT-TYPE
 	 SYNTAX			Integer32
 	 MAX-ACCESS		read-only
 	 STATUS			current 
 	 DESCRIPTION 	
 	         "This object specifies the average delay(microseconds) seen on DMR frames in the test iteration in forward direction."
 	 ::= { wwpLeosCfmExtDelaySessionHistoryEntry 37 }  
    
  wwpLeosCfmExtDelaySessionHistoryForwardMaxDelay OBJECT-TYPE
 	 SYNTAX			Integer32
 	 MAX-ACCESS		read-only
 	 STATUS			current 
 	 DESCRIPTION 	
 	         "This object specifies the maximum delay(microseconds) seen on DMR frames in the test iteration in forward direction."
 	 ::= { wwpLeosCfmExtDelaySessionHistoryEntry 38 } 

   wwpLeosCfmExtDelaySessionHistoryBackwardMinDelay OBJECT-TYPE
 	 SYNTAX			Integer32
 	 MAX-ACCESS		read-only
 	 STATUS			current 
 	 DESCRIPTION 	
 	         "This object specifies the minimum delay(microseconds) seen on DMR frames received in the test iteration in backward direction."
 	 ::= { wwpLeosCfmExtDelaySessionHistoryEntry 39 }
    
  wwpLeosCfmExtDelaySessionHistoryBackwardAveDelay OBJECT-TYPE
 	 SYNTAX			Integer32
 	 MAX-ACCESS		read-only
 	 STATUS			current 
 	 DESCRIPTION 	
 	         "This object specifies the average delay(microseconds) seen on DMR frames in the test iteration in backward direction."
 	 ::= { wwpLeosCfmExtDelaySessionHistoryEntry 40 }  
    
  wwpLeosCfmExtDelaySessionHistoryBackwardMaxDelay OBJECT-TYPE
 	 SYNTAX			Integer32
 	 MAX-ACCESS		read-only
 	 STATUS			current 
 	 DESCRIPTION 	
 	         "This object specifies the maximum delay(microseconds) seen on DMR frames in the test iteration in backward direction."
 	 ::= { wwpLeosCfmExtDelaySessionHistoryEntry 41 } 

  wwpLeosCfmExtDelaySessionHistorySignalDegradeStatus OBJECT-TYPE
         SYNTAX          TruthValue
         MAX-ACCESS      read-only
         STATUS          current
         DESCRIPTION
                 "This object specifies the degrade status in this iteration."
         ::= { wwpLeosCfmExtDelaySessionHistoryEntry 42 }

  wwpLeosCfmExtDelaySessionHistorySignalDegradeSuspect OBJECT-TYPE
         SYNTAX          TruthValue
         MAX-ACCESS      read-only
         STATUS          current
         DESCRIPTION
                 "This object indicates that there was discontinuity in signal degrade monitoring in this iteration.
                  Condition for discontinuity include:
                  a) There is link flapping in this iteration.
                  b) Link is operationally down in this iteration."
         ::= { wwpLeosCfmExtDelaySessionHistoryEntry 43 }

  ---
  --- Delay Responder Table
  ---
 	 
  wwpLeosCfmExtDelayResponderTable OBJECT-TYPE
     SYNTAX     SEQUENCE OF WwpLeosCfmExtDelayResponderEntry
     MAX-ACCESS not-accessible
     STATUS     current
     DESCRIPTION
            "The (conceptual) table lists the Delay responders."            
     ::= { wwpLeosCfmExtDelay 4 }      
     
  wwpLeosCfmExtDelayResponderEntry OBJECT-TYPE
     SYNTAX      WwpLeosCfmExtDelayResponderEntry
     MAX-ACCESS  not-accessible
     STATUS      current
     DESCRIPTION
           "An entry (conceptual row) in the wwpLeosCfmExtDelayResponderTable."      
     INDEX {wwpLeosCfmServiceIndex, wwpLeosCfmExtMEPId, wwpLeosCfmRemoteMEPID}
     ::= { wwpLeosCfmExtDelayResponderTable 1 }  
     
  WwpLeosCfmExtDelayResponderEntry ::=  SEQUENCE {  
     wwpLeosCfmExtDelayResponderServiceName         DisplayString,
     wwpLeosCfmExtDelayResponderLocalMepId          Unsigned32,
     wwpLeosCfmExtDelayResponderLocalMac            MacAddress,     
	 wwpLeosCfmExtDelayResponderRemoteMepid         Unsigned32,
  	 wwpLeosCfmExtDelayResponderRemoteMac		    MacAddress,
     wwpLeosCfmExtDelayResponderAccelerated			TruthValue, 
     wwpLeosCfmExtDelayResponderNumDMMReceived      Unsigned32,
     wwpLeosCfmExtDelayResponderNumDMRSent          Unsigned32
    } 
    
  wwpLeosCfmExtDelayResponderServiceName OBJECT-TYPE
     SYNTAX       DisplayString (SIZE(1..45))
     MAX-ACCESS   read-only
     STATUS       current
     DESCRIPTION
             "This object identifies the CFM service name."
     ::= { wwpLeosCfmExtDelayResponderEntry 1 }  
      
  wwpLeosCfmExtDelayResponderLocalMepId OBJECT-TYPE
     SYNTAX      Unsigned32
     MAX-ACCESS  read-only
     STATUS      current
     DESCRIPTION
             "This object identifies the local mepid."
     ::= { wwpLeosCfmExtDelayResponderEntry 2 } 
     
  wwpLeosCfmExtDelayResponderLocalMac OBJECT-TYPE
     SYNTAX      MacAddress
     MAX-ACCESS  read-only
     STATUS      current
     DESCRIPTION
             "This object identifies the MAC address of the local mep. "
     ::= { wwpLeosCfmExtDelayResponderEntry 3 }  
     
  wwpLeosCfmExtDelayResponderRemoteMepid OBJECT-TYPE
     SYNTAX      	Unsigned32 
     MAX-ACCESS  	read-only
     STATUS      	current
     DESCRIPTION    
             "This object identifies the remote mepid this test is run against."
     ::= { wwpLeosCfmExtDelayResponderEntry 4 }   
    
  wwpLeosCfmExtDelayResponderRemoteMac OBJECT-TYPE
     SYNTAX      MacAddress
     MAX-ACCESS  read-only
     STATUS      current
     DESCRIPTION
             "This object identifies the MAC address of the remote mep."
     ::= { wwpLeosCfmExtDelayResponderEntry 5 }    
     
  wwpLeosCfmExtDelayResponderAccelerated OBJECT-TYPE
     SYNTAX      TruthValue
     MAX-ACCESS  read-only
     STATUS      current
     DESCRIPTION
             "This object identifies if the responder is hardware accelerated or not.
              True if Hardware assisted, False if not. "
     ::= { wwpLeosCfmExtDelayResponderEntry 6 }
     
  wwpLeosCfmExtDelayResponderNumDMMReceived OBJECT-TYPE
     SYNTAX      Unsigned32
     MAX-ACCESS  read-only
     STATUS      current
     DESCRIPTION
             "This object specifies the number of DMM received by this responder." 
     ::= { wwpLeosCfmExtDelayResponderEntry 7 } 
     
  wwpLeosCfmExtDelayResponderNumDMRSent OBJECT-TYPE
     SYNTAX      Unsigned32
     MAX-ACCESS  read-only
     STATUS      current
     DESCRIPTION
             "This object specifies the number of DMR sent by this responder." 
     ::= { wwpLeosCfmExtDelayResponderEntry 8 }

--
-- DMM Bin History Table
--

  wwpLeosCfmExtDelaySessionBinHistoryTable OBJECT-TYPE
     SYNTAX      SEQUENCE OF WwpLeosCfmExtDelaySessionBinHistoryEntry
     MAX-ACCESS  not-accessible
     STATUS      current
     DESCRIPTION "The (conceptual) table listing the Y.1731 Delay
                  Bin History table for the CFM DelaySession"  
     ::= { wwpLeosCfmExtDelay 5}    
     
  wwpLeosCfmExtDelaySessionBinHistoryEntry OBJECT-TYPE
     SYNTAX      WwpLeosCfmExtDelaySessionBinHistoryEntry
     MAX-ACCESS  not-accessible
     STATUS      current
     DESCRIPTION "An entry (conceptual row) in the wwpLeosCfmExtDelaySessionBinHistoryTable."
     INDEX {wwpLeosCfmServiceIndex, wwpLeosCfmExtMEPId,wwpLeosCfmRemoteMEPID,wwpLeosCfmExtDelaySessionTestId ,
            wwpLeosCfmExtDelaySessionHistoryIndex, wwpLeosCfmExtDelaySessionBinHistoryBinType}
     ::= { wwpLeosCfmExtDelaySessionBinHistoryTable 1 }   
 
  WwpLeosCfmExtDelaySessionBinHistoryEntry ::=  SEQUENCE {
     wwpLeosCfmExtDelaySessionBinHistoryBinType                            INTEGER,      
     wwpLeosCfmExtDelaySessionBinHistoryThresholdBin1                      Unsigned32,      
     wwpLeosCfmExtDelaySessionBinHistoryThresholdBin2                      Unsigned32,      
     wwpLeosCfmExtDelaySessionBinHistoryThresholdBin3                      Unsigned32,      
     wwpLeosCfmExtDelaySessionBinHistoryThresholdBin4                      Unsigned32,      
     wwpLeosCfmExtDelaySessionBinHistoryThresholdBin5                      Unsigned32,      
     wwpLeosCfmExtDelaySessionBinHistoryThresholdBin6                      Unsigned32,      
     wwpLeosCfmExtDelaySessionBinHistoryThresholdBin7                      Unsigned32,      
     wwpLeosCfmExtDelaySessionBinHistoryThresholdBin8                      Unsigned32,      
     wwpLeosCfmExtDelaySessionBinHistoryThresholdBin9                      Unsigned32,      
     wwpLeosCfmExtDelaySessionBinHistoryThresholdBin10                     Unsigned32,      
     wwpLeosCfmExtDelaySessionBinHistoryCounterBin0                        Unsigned32,      
     wwpLeosCfmExtDelaySessionBinHistoryCounterBin1                        Unsigned32,      
     wwpLeosCfmExtDelaySessionBinHistoryCounterBin2                        Unsigned32,      
     wwpLeosCfmExtDelaySessionBinHistoryCounterBin3                        Unsigned32,      
     wwpLeosCfmExtDelaySessionBinHistoryCounterBin4                        Unsigned32,      
     wwpLeosCfmExtDelaySessionBinHistoryCounterBin5                        Unsigned32,      
     wwpLeosCfmExtDelaySessionBinHistoryCounterBin6                        Unsigned32,      
     wwpLeosCfmExtDelaySessionBinHistoryCounterBin7                        Unsigned32,      
     wwpLeosCfmExtDelaySessionBinHistoryCounterBin8                        Unsigned32,      
     wwpLeosCfmExtDelaySessionBinHistoryCounterBin9                        Unsigned32,      
     wwpLeosCfmExtDelaySessionBinHistoryCounterBin10                       Unsigned32       
  }
  
  wwpLeosCfmExtDelaySessionBinHistoryBinType OBJECT-TYPE
     SYNTAX       INTEGER 
                  {
                     delay(1),
                     jitter(2),
                     forwardJitter(3),
                     backwardJitter(4)
                  }
     MAX-ACCESS   not-accessible
     STATUS       current
     DESCRIPTION  "This is the history entry index into the table. 
                   This attribute defines the Bin Type. All below attributes holds values for this bintype."
     ::= { wwpLeosCfmExtDelaySessionBinHistoryEntry 1 }

  wwpLeosCfmExtDelaySessionBinHistoryThresholdBin1 OBJECT-TYPE
     SYNTAX        Unsigned32 (0..2147483647)
     MAX-ACCESS    read-only
     STATUS        current
     DESCRIPTION   "The threshold for the Delay Measurement of bintype and bin1, specified
                    in microseconds.  A value of 0 disables the bin. "
     ::= { wwpLeosCfmExtDelaySessionBinHistoryEntry 2 }

  wwpLeosCfmExtDelaySessionBinHistoryThresholdBin2 OBJECT-TYPE
     SYNTAX        Unsigned32 (0..2147483647)
     MAX-ACCESS    read-only
     STATUS        current
     DESCRIPTION   "The threshold for the Delay Measurement of bintype and bin2, specified
                    in microseconds.  A value of 0 disables the bin. "
     ::= { wwpLeosCfmExtDelaySessionBinHistoryEntry 3 }

  wwpLeosCfmExtDelaySessionBinHistoryThresholdBin3 OBJECT-TYPE
     SYNTAX        Unsigned32 (0..2147483647)
     MAX-ACCESS    read-only
     STATUS        current
     DESCRIPTION   "The threshold for the Delay Measurement of bintype and bin3, specified
                    in microseconds.  A value of 0 disables the bin. "
     ::= { wwpLeosCfmExtDelaySessionBinHistoryEntry 4 }

  wwpLeosCfmExtDelaySessionBinHistoryThresholdBin4 OBJECT-TYPE
     SYNTAX        Unsigned32 (0..2147483647)
     MAX-ACCESS    read-only
     STATUS        current
     DESCRIPTION   "The threshold for the Delay Measurement of bintype and bin4, specified
                    in microseconds.  A value of 0 disables the bin. "
     ::= { wwpLeosCfmExtDelaySessionBinHistoryEntry 5 }

  wwpLeosCfmExtDelaySessionBinHistoryThresholdBin5 OBJECT-TYPE
     SYNTAX        Unsigned32 (0..2147483647)
     MAX-ACCESS    read-only
     STATUS        current
     DESCRIPTION   "The threshold for the Delay Measurement of bintype and bin5, specified
                    in microseconds.  A value of 0 disables the bin. "
     ::= { wwpLeosCfmExtDelaySessionBinHistoryEntry 6 }

  wwpLeosCfmExtDelaySessionBinHistoryThresholdBin6 OBJECT-TYPE
     SYNTAX        Unsigned32 (0..2147483647)
     MAX-ACCESS    read-only
     STATUS        current
     DESCRIPTION   "The threshold for the Delay Measurement of bintype and bin6, specified
                    in microseconds.  A value of 0 disables the bin. "
     ::= { wwpLeosCfmExtDelaySessionBinHistoryEntry 7 }

  wwpLeosCfmExtDelaySessionBinHistoryThresholdBin7 OBJECT-TYPE
     SYNTAX        Unsigned32 (0..2147483647)
     MAX-ACCESS    read-only
     STATUS        current
     DESCRIPTION   "The threshold for the Delay Measurement of bintype and bin7, specified
                    in microseconds.  A value of 0 disables the bin. "
     ::= { wwpLeosCfmExtDelaySessionBinHistoryEntry 8 }

  wwpLeosCfmExtDelaySessionBinHistoryThresholdBin8 OBJECT-TYPE
     SYNTAX        Unsigned32 (0..2147483647)
     MAX-ACCESS    read-only
     STATUS        current
     DESCRIPTION   "The threshold for the Delay Measurement of bintype and bin8, specified
                    in microseconds.  A value of 0 disables the bin. "
     ::= { wwpLeosCfmExtDelaySessionBinHistoryEntry 9 }

  wwpLeosCfmExtDelaySessionBinHistoryThresholdBin9 OBJECT-TYPE
     SYNTAX        Unsigned32 (0..2147483647)
     MAX-ACCESS    read-only
     STATUS        current
     DESCRIPTION   "The threshold for the Delay Measurement of bintype and bin9, specified
                    in microseconds.  A value of 0 disables the bin. "
     ::= { wwpLeosCfmExtDelaySessionBinHistoryEntry 10 }

  wwpLeosCfmExtDelaySessionBinHistoryThresholdBin10 OBJECT-TYPE
     SYNTAX        Unsigned32 (0..2147483647)
     MAX-ACCESS    read-only
     STATUS        current
     DESCRIPTION   "The threshold for the Delay Measurement of bintype and bin10, specified
                    in microseconds.  A value of 0 disables the bin. "
     ::= { wwpLeosCfmExtDelaySessionBinHistoryEntry 11 }

  wwpLeosCfmExtDelaySessionBinHistoryCounterBin0 OBJECT-TYPE
     SYNTAX       Unsigned32
     MAX-ACCESS   read-only
     STATUS       current
     DESCRIPTION  "This object counters the number of frame delay measurements whose measured bintype attribute falls into a threshold range Bin 0."
     ::= { wwpLeosCfmExtDelaySessionBinHistoryEntry 12 }

  wwpLeosCfmExtDelaySessionBinHistoryCounterBin1 OBJECT-TYPE
     SYNTAX       Unsigned32
     MAX-ACCESS   read-only
     STATUS       current
     DESCRIPTION  "This object counters the number of frame delay measurements whose measured bintype attribute falls into a threshold range Bin 1."
     ::= { wwpLeosCfmExtDelaySessionBinHistoryEntry 13 }

  wwpLeosCfmExtDelaySessionBinHistoryCounterBin2 OBJECT-TYPE
     SYNTAX       Unsigned32
     MAX-ACCESS   read-only
     STATUS       current
     DESCRIPTION  "This object counters the number of frame delay measurements whose measured bintype attribute falls into a threshold range Bin 2."
     ::= { wwpLeosCfmExtDelaySessionBinHistoryEntry 14 }

  wwpLeosCfmExtDelaySessionBinHistoryCounterBin3 OBJECT-TYPE
     SYNTAX       Unsigned32
     MAX-ACCESS   read-only
     STATUS       current
     DESCRIPTION  "This object counters the number of frame delay measurements whose measured bintype attribute falls into a threshold range Bin 3."
     ::= { wwpLeosCfmExtDelaySessionBinHistoryEntry 15 }

  wwpLeosCfmExtDelaySessionBinHistoryCounterBin4 OBJECT-TYPE
     SYNTAX       Unsigned32
     MAX-ACCESS   read-only
     STATUS       current
     DESCRIPTION  "This object counters the number of frame delay measurements whose measured bintype attribute falls into a threshold range Bin 4."
     ::= { wwpLeosCfmExtDelaySessionBinHistoryEntry 16 }

  wwpLeosCfmExtDelaySessionBinHistoryCounterBin5 OBJECT-TYPE
     SYNTAX       Unsigned32
     MAX-ACCESS   read-only
     STATUS       current
     DESCRIPTION  "This object counters the number of frame delay measurements whose measured bintype attribute falls into a threshold range Bin 5."
     ::= { wwpLeosCfmExtDelaySessionBinHistoryEntry 17 }

  wwpLeosCfmExtDelaySessionBinHistoryCounterBin6 OBJECT-TYPE
     SYNTAX       Unsigned32
     MAX-ACCESS   read-only
     STATUS       current
     DESCRIPTION  "This object counters the number of frame delay measurements whose measured bintype attribute falls into a threshold range Bin 6."
     ::= { wwpLeosCfmExtDelaySessionBinHistoryEntry 18 }

  wwpLeosCfmExtDelaySessionBinHistoryCounterBin7 OBJECT-TYPE
     SYNTAX       Unsigned32
     MAX-ACCESS   read-only
     STATUS       current
     DESCRIPTION  "This object counters the number of frame delay measurements whose measured bintype attribute falls into a threshold range Bin 7."
     ::= { wwpLeosCfmExtDelaySessionBinHistoryEntry 19 }

  wwpLeosCfmExtDelaySessionBinHistoryCounterBin8 OBJECT-TYPE
     SYNTAX       Unsigned32
     MAX-ACCESS   read-only
     STATUS       current
     DESCRIPTION  "This object counters the number of frame delay measurements whose measured bintype attribute falls into a threshold range Bin 8."
     ::= { wwpLeosCfmExtDelaySessionBinHistoryEntry 20 }

  wwpLeosCfmExtDelaySessionBinHistoryCounterBin9 OBJECT-TYPE
     SYNTAX       Unsigned32
     MAX-ACCESS   read-only
     STATUS       current
     DESCRIPTION  "This object counters the number of frame delay measurements whose measured bintype attribute falls into a threshold range Bin 9."
     ::= { wwpLeosCfmExtDelaySessionBinHistoryEntry 21 }

  wwpLeosCfmExtDelaySessionBinHistoryCounterBin10 OBJECT-TYPE
     SYNTAX       Unsigned32
     MAX-ACCESS   read-only
     STATUS       current
     DESCRIPTION  "This object counters the number of frame delay measurements whose measured bintype attribute falls into a threshold range Bin 10."
     ::= { wwpLeosCfmExtDelaySessionBinHistoryEntry 22 }

  ---
  --- Delay Responder Table extension
  ---
 	 
  wwpLeosCfmExt2DelayResponderTable OBJECT-TYPE
     SYNTAX     SEQUENCE OF WwpLeosCfmExt2DelayResponderEntry
     MAX-ACCESS not-accessible
     STATUS     current
     DESCRIPTION
            "The (conceptual) table lists the Delay responders indexed based on (service, localmep, remotemep, test ID)."
     ::= { wwpLeosCfmExtDelay 6 }
     
  wwpLeosCfmExt2DelayResponderEntry OBJECT-TYPE
     SYNTAX      WwpLeosCfmExt2DelayResponderEntry
     MAX-ACCESS  not-accessible
     STATUS      current
     DESCRIPTION
           "An entry (conceptual row) in the wwpLeosCfmExt2DelayResponderTable."
     INDEX {wwpLeosCfmServiceIndex, wwpLeosCfmExtMEPId, wwpLeosCfmRemoteMEPID, wwpLeosCfmExt2DelayResponderTestId}
     ::= { wwpLeosCfmExt2DelayResponderTable 1 }
     
  WwpLeosCfmExt2DelayResponderEntry ::=  SEQUENCE {
     wwpLeosCfmExt2DelayResponderTestId              Unsigned32,
     wwpLeosCfmExt2DelayResponderServiceName         DisplayString,
     wwpLeosCfmExt2DelayResponderLocalMepId          Unsigned32,
     wwpLeosCfmExt2DelayResponderLocalMac            MacAddress,
	 wwpLeosCfmExt2DelayResponderRemoteMepid         Unsigned32,
  	 wwpLeosCfmExt2DelayResponderRemoteMac           MacAddress,
     wwpLeosCfmExt2DelayResponderAccelerated         TruthValue,
     wwpLeosCfmExt2DelayResponderNumDMMReceived      Unsigned32,
     wwpLeosCfmExt2DelayResponderNumDMRSent          Unsigned32,
     wwpLeosCfmExt2DelayResponderTimestampType       CfmTimestampType
    } 

  wwpLeosCfmExt2DelayResponderTestId OBJECT-TYPE
     SYNTAX       Unsigned32 (0..4294967295)
     MAX-ACCESS   not-accessible
     STATUS       current
     DESCRIPTION
              "This object specifies the test ID configured for the Delay Responder session."
     ::= { wwpLeosCfmExt2DelayResponderEntry 1 }

  wwpLeosCfmExt2DelayResponderServiceName OBJECT-TYPE
     SYNTAX       DisplayString (SIZE(1..45))
     MAX-ACCESS   read-only
     STATUS       current
     DESCRIPTION
             "This object identifies the CFM service name."
     ::= { wwpLeosCfmExt2DelayResponderEntry 2 }

  wwpLeosCfmExt2DelayResponderLocalMepId OBJECT-TYPE
     SYNTAX      Unsigned32
     MAX-ACCESS  read-only
     STATUS      current
     DESCRIPTION
             "This object identifies the local mepid."
     ::= { wwpLeosCfmExt2DelayResponderEntry 3 }

  wwpLeosCfmExt2DelayResponderLocalMac OBJECT-TYPE
     SYNTAX      MacAddress
     MAX-ACCESS  read-only
     STATUS      current
     DESCRIPTION
             "This object identifies the MAC address of the local mep. "
     ::= { wwpLeosCfmExt2DelayResponderEntry 4 }

  wwpLeosCfmExt2DelayResponderRemoteMepid OBJECT-TYPE
     SYNTAX      	Unsigned32
     MAX-ACCESS  	read-only
     STATUS      	current
     DESCRIPTION
             "This object identifies the remote mepid this test is run against."
     ::= { wwpLeosCfmExt2DelayResponderEntry 5 }

  wwpLeosCfmExt2DelayResponderRemoteMac OBJECT-TYPE
     SYNTAX      MacAddress
     MAX-ACCESS  read-only
     STATUS      current
     DESCRIPTION
             "This object identifies the MAC address of the remote mep."
     ::= { wwpLeosCfmExt2DelayResponderEntry 6 }

  wwpLeosCfmExt2DelayResponderAccelerated OBJECT-TYPE
     SYNTAX      TruthValue
     MAX-ACCESS  read-only
     STATUS      current
     DESCRIPTION
             "This object identifies if the responder is hardware accelerated or not.
              True if Hardware assisted, False if not."
     ::= { wwpLeosCfmExt2DelayResponderEntry 7 }

  wwpLeosCfmExt2DelayResponderNumDMMReceived OBJECT-TYPE
     SYNTAX      Unsigned32
     MAX-ACCESS  read-only
     STATUS      current
     DESCRIPTION
             "This object specifies the number of DMM received by this responder."
     ::= { wwpLeosCfmExt2DelayResponderEntry 8 }

  wwpLeosCfmExt2DelayResponderNumDMRSent OBJECT-TYPE
     SYNTAX      Unsigned32
     MAX-ACCESS  read-only
     STATUS      current
     DESCRIPTION
             "This object specifies the number of DMR sent by this responder."
     ::= { wwpLeosCfmExt2DelayResponderEntry 9 }

  wwpLeosCfmExt2DelayResponderTimestampType OBJECT-TYPE
     SYNTAX       CfmTimestampType
     MAX-ACCESS   read-only
     STATUS       current
     DESCRIPTION
             "This object specifies the timestamp type to be embedded in incoming DMM and outgoing DMR Frames at Delay Responder."
     DEFVAL       {hardware}
     ::= { wwpLeosCfmExt2DelayResponderEntry 10 }
  
  --
  -- Frame Loss Measurement Msg table
  -- 
  wwpLeosCfmExtFrameLossMsgTable OBJECT-TYPE
     SYNTAX     SEQUENCE OF WwpLeosCfmExtFrameLossMsgEntry
     MAX-ACCESS not-accessible
     STATUS     current
     DESCRIPTION
            "The (conceptual) table listing the configuration
            parameters for the FrameLossMeasurementMsg."  
     ::= { wwpLeosCfmExtFrameLoss 1 }
                
 wwpLeosCfmExtFrameLossMsgEntry OBJECT-TYPE
     SYNTAX      WwpLeosCfmExtFrameLossMsgEntry
     MAX-ACCESS  not-accessible
     STATUS      current
     DESCRIPTION
           "An entry (conceptual row) in the wwpLeosCfmFrameLossMsgTable.
           To send, clear or cancel the message, the corresponding MsgAction
           needs to be specified. Individual objects in this table
           cannot be set. RowStatus is a read-only field.
           To send or cancel a message, the TargetMepID or the
           TargtetMacAddr objects need to be specified.
           Clear msgAction clears the counters for the message"
     --wwpLeosCfmExtFrameLossMsgLocalMEPId is a new index in place of framelossmsgportId
     INDEX {wwpLeosCfmServiceIndex, wwpLeosCfmExtFrameLossMsgLocalMEPId}
     ::= { wwpLeosCfmExtFrameLossMsgTable 1 }
                
 WwpLeosCfmExtFrameLossMsgEntry ::=  SEQUENCE { 
     wwpLeosCfmExtFrameLossMsgLocalMEPId                  	INTEGER,
     wwpLeosCfmExtFrameLossMsgTargetMEPID              Unsigned32,
     wwpLeosCfmExtFrameLossMsgTargetMacAddr            MacAddress,
     wwpLeosCfmExtFrameLossMsgCount                   	INTEGER,
     wwpLeosCfmExtFrameLossMsgPriority                	INTEGER,
     wwpLeosCfmExtFrameLossMsgRepeat					INTEGER,
     wwpLeosCfmExtFrameLossMsgRepeatCount				INTEGER,
     wwpLeosCfmExtFrameLossMsgFlnThreshold				INTEGER,
     wwpLeosCfmExtFrameLossMsgFlfThreshold				INTEGER,
     wwpLeosCfmExtFrameLossMsgAction					SendState,
     wwpLeosCfmExtFrameLossMsgSeqThreshold				INTEGER     
 
 }
  wwpLeosCfmExtFrameLossMsgLocalMEPId OBJECT-TYPE
     SYNTAX       INTEGER (1..65535)
     MAX-ACCESS   not-accessible
     STATUS       current
     DESCRIPTION
             "This object specifies the Local MEPID at the source."
     ::= { wwpLeosCfmExtFrameLossMsgEntry 1 }
 
 wwpLeosCfmExtFrameLossMsgTargetMEPID OBJECT-TYPE
     SYNTAX       Unsigned32 (1..8191)
     MAX-ACCESS   read-create
     STATUS       current
     DESCRIPTION
             "This object specifies the MEPID.
              This object should only be set if wwpLeosCfmExtFrameLossMsgTargetMacAddr is not specified else
              an error is returned."
     ::= { wwpLeosCfmExtFrameLossMsgEntry 2 }
     
 wwpLeosCfmExtFrameLossMsgTargetMacAddr OBJECT-TYPE
     SYNTAX       MacAddress
     MAX-ACCESS   read-create
     STATUS       current
     DESCRIPTION
             "This object specifies the MAC address to be used when sending link LoopbackMsg.
              This object should only be set if wwpLeosCfmExtFrameLossMsgTargetMEPID is not specified else
              an error is returned."
     ::= { wwpLeosCfmExtFrameLossMsgEntry 3 }
     
 wwpLeosCfmExtFrameLossMsgCount OBJECT-TYPE
     SYNTAX       INTEGER (2..600) 
     MAX-ACCESS   read-create
     STATUS       current
     DESCRIPTION
             "This object specifies the FrameLossMeasurementMsg count to be used
              when sending link FrameLossMeasurementMsg."
     ::= { wwpLeosCfmExtFrameLossMsgEntry 4 }
 
 wwpLeosCfmExtFrameLossMsgPriority OBJECT-TYPE
     SYNTAX       INTEGER (0..7)
     MAX-ACCESS   read-create
     STATUS       current
     DESCRIPTION
             "This object specifies the FrameLossMeasurementMsg priority to be
             used when sending link FrameLossMeasurementMsg."
     ::= { wwpLeosCfmExtFrameLossMsgEntry 5 }
 

  wwpLeosCfmExtFrameLossMsgRepeat OBJECT-TYPE
 	 SYNTAX			INTEGER {
 	 					enable(1),
 	 					disable(2)
 	 					}
 	 MAX-ACCESS		read-create
 	 STATUS			current
 	 DESCRIPTION
 	     "Used to make the Frame Loss Measurement test a repeating test."
 	 ::= { wwpLeosCfmExtFrameLossMsgEntry 8 } 
 	 
 wwpLeosCfmExtFrameLossMsgRepeatCount OBJECT-TYPE
 	SYNTAX			INTEGER (0..1440)
 	MAX-ACCESS		read-create
 	STATUS			current
 	DESCRIPTION
 	     "This object specifies the repeat time in minutes for the Frame Loss Measurement test.
	     If zero is specified, the test runs continuously."
 	::= { wwpLeosCfmExtFrameLossMsgEntry 9 } 
 	
  wwpLeosCfmExtFrameLossMsgFlnThreshold OBJECT-TYPE
 	SYNTAX			INTEGER (-1..600)
 	MAX-ACCESS		read-create
 	STATUS			current
 	DESCRIPTION
 			"The fault threshold for the Frame Loss Measurement test.
 			A value of -1 disables the generate of faults. A value of 0 or greater
 			iscompared to the frame loss near result of the
 			test and a fault is generated if the threshold is exceeded."
 	::= { wwpLeosCfmExtFrameLossMsgEntry 10 }
 
 wwpLeosCfmExtFrameLossMsgFlfThreshold OBJECT-TYPE
 	SYNTAX			INTEGER (-1..600)
 	MAX-ACCESS		read-create
 	STATUS			current
 	DESCRIPTION
 			"The fault threshold for the Frame Loss Measurement test.
 			A value of -1 disables the generate of faults. A value of 0 or greater
 			iscompared to the frame loss far result of the
 			test and a fault is generated if the threshold is exceeded."
 	::= { wwpLeosCfmExtFrameLossMsgEntry 11 }   
 
  
 wwpLeosCfmExtFrameLossMsgAction OBJECT-TYPE
     SYNTAX       SendState
     MAX-ACCESS   read-create
     STATUS       current
     DESCRIPTION
             "This object represents the action for the message (send, clear or cancel)
             This object represents the action for the message (send, clear or cancel)
             If set to send(1) and if wwpLeosCfmExtFrameLossMacAddr is specified
             then FrameLoss is sent to remote MAC.
             If set to send(1) and if wwpLeosCfmExtFrameLossMsgTargetMEPID is specified
             then FrameLossMsg is sent to remote mepid.
             Setting to clear(2), clears the mep statistics for given service and mepid.
             If set to cancel(3) and if wwpLeosCfmExtFrameLossMsgTargetMacAddr is specified
             then it cancels sending FrameLoss Messages to remoteMac.
             If set to cancel(3) and if wwpLeosCfmExtFrameLossMsgTargetMEPID is specified
             then it cancels sending FrameLoss messages to remoteMEPID."
     ::= { wwpLeosCfmExtFrameLossMsgEntry 12 }  
  
 wwpLeosCfmExtFrameLossMsgSeqThreshold	OBJECT-TYPE
 	SYNTAX			INTEGER (-1..600)
 	MAX-ACCESS		read-create
 	STATUS			current
 	DESCRIPTION
 			"The sequence threshold for the Frame Loss Measurement test.
 			A value of -1 disables the generate of faults. A value of 0 or greater
 			is compared to the frame loss far result of the
 			test and a fault is generated if the threshold is exceeded."
 	::= { wwpLeosCfmExtFrameLossMsgEntry 13 }   

  --
  -- Frame Loss Measurement Multiple CoS Msg table
  -- 
  wwpLeosCfmExtFrameLossSessionTable OBJECT-TYPE
     SYNTAX     SEQUENCE OF WwpLeosCfmExtFrameLossSessionEntry
     MAX-ACCESS not-accessible
     STATUS     current
     DESCRIPTION
            "The (conceptual) table listing the configuration
            parameters for the FrameLossMeasurementMsg."  
     ::= { wwpLeosCfmExtFrameLoss 2 } 
     
  wwpLeosCfmExtFrameLossSessionEntry OBJECT-TYPE
     SYNTAX      WwpLeosCfmExtFrameLossSessionEntry
     MAX-ACCESS  not-accessible
     STATUS      current
     DESCRIPTION
           "An entry (conceptual row) in the wwpLeosCfmExtFrameLossSessionTable.
           To send, clear or cancel the message, the corresponding MsgAction
           needs to be specified. Individual objects in this table
           cannot be set."
     INDEX {wwpLeosCfmServiceIndex, wwpLeosCfmExtMEPId,wwpLeosCfmRemoteMEPID,
            wwpLeosCfmExtFrameLossSessionTestId}
     ::= { wwpLeosCfmExtFrameLossSessionTable 1 }  
     
  WwpLeosCfmExtFrameLossSessionEntry ::=  SEQUENCE {           
     wwpLeosCfmExtFrameLossSessionTestId                   Unsigned32,
     wwpLeosCfmExtFrameLossSessionPriority                 Unsigned32,
	 wwpLeosCfmExtFrameLossSessionCount                    Unsigned32, 
	 wwpLeosCfmExtFrameLossSessionLMMInterval              Unsigned32,
     wwpLeosCfmExtFrameLossSessionIterations			   Unsigned32,
     wwpLeosCfmExtFrameLossSessionRepeatDelay			   Unsigned32,
     wwpLeosCfmExtFrameLossSessionTimeout                  Unsigned32,
     wwpLeosCfmExtFrameLossSessionFrameLossNearThreshold   Integer32,
     wwpLeosCfmExtFrameLossSessionFrameLossFarThreshold	   Integer32,
     wwpLeosCfmExtFrameLossSessionSeqThreshold			   Integer32,
     wwpLeosCfmExtFrameLossSessionDuration                 Unsigned32, 
     wwpLeosCfmExtFrameLossSessionAccelerated              TruthValue, 
     wwpLeosCfmExtFrameLossSessionDataPriority             INTEGER,
     wwpLeosCfmExtFrameLossSessionAction				   SendState,
     wwpLeosCfmExtFrameLossSessionNumLMMSent         	   Unsigned32,
     wwpLeosCfmExtFrameLossSessionNumLMRReceived     	   Unsigned32,
     wwpLeosCfmExtFrameLossSessionFrameLossNear            Integer32,
     wwpLeosCfmExtFrameLossSessionFrameLossFar             Integer32,
     wwpLeosCfmExtFrameLossSessionAvgFrameLossNear         Integer32,
     wwpLeosCfmExtFrameLossSessionMinFrameLossNear         Integer32,
     wwpLeosCfmExtFrameLossSessionMaxFrameLossNear         Integer32,
     wwpLeosCfmExtFrameLossSessionAvgFrameLossFar          Integer32,
     wwpLeosCfmExtFrameLossSessionMinFrameLossFar          Integer32,
     wwpLeosCfmExtFrameLossSessionMaxFrameLossFar          Integer32,      
     wwpLeosCfmExtFrameLossSessionFrameLossRatioNear       CfmFrameLossRatio,
     wwpLeosCfmExtFrameLossSessionFrameLossRatioFar        CfmFrameLossRatio,
     wwpLeosCfmExtFrameLossSessionTxFCfStart               Unsigned32,
     wwpLeosCfmExtFrameLossSessionTxFCfEnd                 Unsigned32,
     wwpLeosCfmExtFrameLossSessionRxFCfStart               Unsigned32,
     wwpLeosCfmExtFrameLossSessionRxFCfEnd                 Unsigned32,
     wwpLeosCfmExtFrameLossSessionTxFCbStart               Unsigned32,
     wwpLeosCfmExtFrameLossSessionTxFCbEnd                 Unsigned32,
     wwpLeosCfmExtFrameLossSessionRxFClStart               Unsigned32,
     wwpLeosCfmExtFrameLossSessionRxFClEnd                 Unsigned32,
     wwpLeosCfmExtFrameLossSessionConfigAccelerated        TruthValue 
  }   
 
  wwpLeosCfmExtFrameLossSessionTestId OBJECT-TYPE
     SYNTAX       Unsigned32 (0..4294967295)
     MAX-ACCESS   not-accessible
     STATUS       current
     DESCRIPTION
             "This object specifies the LMM test id to be used when sending link FrameLossMeasurementMsg."
     ::= { wwpLeosCfmExtFrameLossSessionEntry 1 }   
     
  wwpLeosCfmExtFrameLossSessionPriority OBJECT-TYPE
     SYNTAX       Unsigned32 (0..7)
     MAX-ACCESS   read-write
     STATUS       current
     DESCRIPTION
             "This object specifies the LMM priority to be used when sending link FrameLossMeasurementMsg. 
	     Recommended to set this object when performing SET operation."
     ::= { wwpLeosCfmExtFrameLossSessionEntry 2 }  
     
  wwpLeosCfmExtFrameLossSessionCount OBJECT-TYPE
     SYNTAX       Unsigned32 (0 | 2..65535) 
     MAX-ACCESS   read-create
     STATUS       current
     DESCRIPTION
             "This object specifies the LMM count to be used
              when sending link FrameLossMeasurementMsg."
     ::= { wwpLeosCfmExtFrameLossSessionEntry 3 }    
     
  wwpLeosCfmExtFrameLossSessionLMMInterval  OBJECT-TYPE
     SYNTAX       Unsigned32 (0..7)
     MAX-ACCESS   read-create
     STATUS       current
     DESCRIPTION
             "This object specifies the LMM transmission intervals.
	      If set to Zero, CFM global default interval setting is applied.
              The values 1-7 represent indices to CFM intervals as follows:
              1 --> 3.33ms,
              2 --> 10ms,
              3 --> 100ms,
              4 --> 1sec,
              5 --> 10sec,
              6 --> 1min,
              7 --> 10min."
     ::= { wwpLeosCfmExtFrameLossSessionEntry 4 }
     
  wwpLeosCfmExtFrameLossSessionIterations OBJECT-TYPE
 	 SYNTAX			Unsigned32 (0..60)
 	 MAX-ACCESS		read-create
 	 STATUS			current
 	 DESCRIPTION
 	 		 "This object specifies the number of iterations the test
              has to be conducted. Each test iteration is defined by wwpLeosCfmExtFrameLossSessionLMMInterval,
              wwpLeosCfmExtFrameLossSessionCount. Whereas, the test sessions is defined by test iterations over
              wwpLeosCfmExtFrameLossSessionRepeatDelay.
              
              If this object is set to zero, it means that test is continuous, and iterations are infinite. "
 	 ::= { wwpLeosCfmExtFrameLossSessionEntry 5 } 
 	 
  wwpLeosCfmExtFrameLossSessionRepeatDelay OBJECT-TYPE
 	 SYNTAX			Unsigned32 (0..1440)
 	 MAX-ACCESS		read-create
 	 STATUS			current
 	 DESCRIPTION
 			 "This object specifies the delay in minutes between consecutive test iterations."
 	::= { wwpLeosCfmExtFrameLossSessionEntry 6 } 
 	     
  wwpLeosCfmExtFrameLossSessionTimeout  OBJECT-TYPE  
     SYNTAX       Unsigned32 (0 | 2000..10000)
     MAX-ACCESS   read-create
     STATUS       current
     DESCRIPTION
             "This object specifies the timeout interval in milliseconds within which
              the source should Rx a LMR for a corresponding LMM Msg.
              If this object is set to zero, the CFM global default setting is applied."
     ::= { wwpLeosCfmExtFrameLossSessionEntry 7 } 
 	
  wwpLeosCfmExtFrameLossSessionFrameLossNearThreshold OBJECT-TYPE
 	 SYNTAX			Integer32 (-1..2147483647)
 	 MAX-ACCESS		read-create
 	 STATUS			current
 	 DESCRIPTION
 			 "The fault threshold for the Frame Loss Measurement test.
 			 A value of -1 disables the generate of faults. A value of 0 or greater
 			 is compared to the frame loss near result of the
 			 test and a fault is generated if the threshold is exceeded."
 	 ::= { wwpLeosCfmExtFrameLossSessionEntry 8 }
 	
  wwpLeosCfmExtFrameLossSessionFrameLossFarThreshold OBJECT-TYPE
 	 SYNTAX			Integer32 (-1..2147483647)
 	 MAX-ACCESS		read-create
 	 STATUS			current
 	 DESCRIPTION
 			 "The fault threshold for the Frame Loss Measurement test.
 			 A value of -1 disables the generate of faults. A value of 0 or greater
 			 is compared to the frame loss far result of the
 			 test and a fault is generated if the threshold is exceeded."
 	 ::= { wwpLeosCfmExtFrameLossSessionEntry 9 } 
 	   
  wwpLeosCfmExtFrameLossSessionSeqThreshold	OBJECT-TYPE
 	 SYNTAX			Integer32 (-1..65535)
 	 MAX-ACCESS		read-create
 	 STATUS			current
 	 DESCRIPTION
 			 "The sequence threshold for the Frame Loss Measurement test.
 			 A value of -1 disables the generate of faults. As value of 0 or greater
 			 is compared to the frame loss far result of the
 			 test and a fault is generated if the threshold is exceeded."
 	 ::= { wwpLeosCfmExtFrameLossSessionEntry 10 } 
 	      
  wwpLeosCfmExtFrameLossSessionDuration OBJECT-TYPE
 	 SYNTAX			Unsigned32 (0..65535)
 	 MAX-ACCESS		read-create
 	 STATUS			current                                   
 	 DESCRIPTION
 		     "This object is used to set/read the duration of time the test took to complete one iteration."
 	 ::= { wwpLeosCfmExtFrameLossSessionEntry 11 } 
 	
  wwpLeosCfmExtFrameLossSessionAccelerated	OBJECT-TYPE
 	 SYNTAX			TruthValue
 	 MAX-ACCESS		read-create
 	 STATUS			current
 	 DESCRIPTION
 	     "Setting this attribute to true gathers loss measurements in hardware. 
             This object returns true if loss sender is actively utilizing hardware resources."
 	 ::= { wwpLeosCfmExtFrameLossSessionEntry 12 }    
 	 
  wwpLeosCfmExtFrameLossSessionDataPriority	OBJECT-TYPE
 	 SYNTAX			INTEGER 
 	                {  zero(0),
 	                   one(1),
 	                   two(2),
 	                   three(3),
 	                   four(4),
 	                   five(5),
 	                   six(6),
 	                   seven(7),
 	                   all(8)
 	                }
 	 MAX-ACCESS		read-create
 	 STATUS			current
 	 DESCRIPTION
 			 "This object is used to set the data traffic priority. 
			 Recommended to set this object when performing	SET operation."
 	 ::= { wwpLeosCfmExtFrameLossSessionEntry 13 } 
 	 
  wwpLeosCfmExtFrameLossSessionAction OBJECT-TYPE
     SYNTAX       SendState
     MAX-ACCESS   read-create
     STATUS       current
     DESCRIPTION
             "This object represents the action for the message (send, clear, delete or cancel)
             If set to send(1) and if wwpLeosCfmRemoteMEPID is specified
             then FrameLossMsg is sent to remote mepid.
             Setting to clear(2) clears mep statistics for given service and mepid.
             If set to cancel(3) and if wwpLeosCfmRemoteMEPID is specified
             then it cancels sending FrameLoss messages to remoteMEPID.
             If set to delete(4) test is deleted for this specific testid."
     ::= { wwpLeosCfmExtFrameLossSessionEntry 14 }  
     
  wwpLeosCfmExtFrameLossSessionNumLMMSent OBJECT-TYPE
 	  SYNTAX			Unsigned32 (1..65535)
 	  MAX-ACCESS		read-only
 	  STATUS			current
 	  DESCRIPTION
 	    "This object specifies the number of LMM sent in the last iteration of the completed test."
 	  ::= { wwpLeosCfmExtFrameLossSessionEntry 15 }

   wwpLeosCfmExtFrameLossSessionNumLMRReceived OBJECT-TYPE
 	  SYNTAX			Unsigned32 (1..65535)
 	  MAX-ACCESS		read-only
 	  STATUS			current
 	  DESCRIPTION
 	     "This object specifies the number of LMR received in the last iteration of the completed test."
 	  ::= { wwpLeosCfmExtFrameLossSessionEntry 16 }
 	  
  wwpLeosCfmExtFrameLossSessionFrameLossNear OBJECT-TYPE
 	  SYNTAX			Integer32 
 	  MAX-ACCESS		read-only
 	  STATUS			current
 	  DESCRIPTION
 	     "This object specifies the near loss threshold in the last iteration of the completed test."
 	  ::= { wwpLeosCfmExtFrameLossSessionEntry 17 }
 	  
  wwpLeosCfmExtFrameLossSessionFrameLossFar OBJECT-TYPE
 	  SYNTAX			Integer32
 	  MAX-ACCESS		read-only
 	  STATUS			current
 	  DESCRIPTION
 	     "This object specifies the far loss threshold in the last iteration of the completed test."
 	  ::= { wwpLeosCfmExtFrameLossSessionEntry 18 }
 	  
  wwpLeosCfmExtFrameLossSessionAvgFrameLossNear OBJECT-TYPE
 	  SYNTAX			Integer32 
 	  MAX-ACCESS		read-only
 	  STATUS			current
 	  DESCRIPTION
 	     "This object specifies the average near loss threshold in the last iteration of the completed test."
 	  ::= { wwpLeosCfmExtFrameLossSessionEntry 19 }
 	  
  wwpLeosCfmExtFrameLossSessionMinFrameLossNear OBJECT-TYPE
 	  SYNTAX			Integer32 
 	  MAX-ACCESS		read-only
 	  STATUS			current
 	  DESCRIPTION
 	     "This object specifies the minimum Near Loss Threshold in the last iteration of the completed test."
 	  ::= { wwpLeosCfmExtFrameLossSessionEntry 20 }
 	  
  wwpLeosCfmExtFrameLossSessionMaxFrameLossNear OBJECT-TYPE
 	  SYNTAX			Integer32 
 	  MAX-ACCESS		read-only
 	  STATUS			current
 	  DESCRIPTION
 	     "This object specifies the maximum Near Loss Threshold in the last iteration of the completed test."
 	  ::= { wwpLeosCfmExtFrameLossSessionEntry 21 }
 	  
  wwpLeosCfmExtFrameLossSessionAvgFrameLossFar OBJECT-TYPE
 	  SYNTAX			Integer32 
 	  MAX-ACCESS		read-only
 	  STATUS			current
 	  DESCRIPTION
 	      "This object specifies the average Far Loss Thrsshold in the last iteration of the completed test."
 	  ::= { wwpLeosCfmExtFrameLossSessionEntry 22 }
 	  
  wwpLeosCfmExtFrameLossSessionMinFrameLossFar OBJECT-TYPE
 	  SYNTAX			Integer32 
 	  MAX-ACCESS		read-only
 	  STATUS			current
 	  DESCRIPTION
 	      "This object specifies the minimum Far Loss Threshold in the last iteration of the completed test."
 	  ::= { wwpLeosCfmExtFrameLossSessionEntry 23 }
 	  
  wwpLeosCfmExtFrameLossSessionMaxFrameLossFar OBJECT-TYPE
 	  SYNTAX			Integer32 
 	  MAX-ACCESS		read-only
 	  STATUS			current
 	  DESCRIPTION
 	      "This object specifies the maximum Far Loss Threshold in the last iteration of the completed test."
 	  ::= { wwpLeosCfmExtFrameLossSessionEntry 24 } 

  wwpLeosCfmExtFrameLossSessionFrameLossRatioNear OBJECT-TYPE
 	  SYNTAX			CfmFrameLossRatio
 	  MAX-ACCESS		read-only
 	  STATUS			current
 	  DESCRIPTION
 	     "This object specifies the Frame Loss Ratio in percentile of loss at Nearend in the last iteration
              of the completed test."
 	  ::= { wwpLeosCfmExtFrameLossSessionEntry 25 }
 	  
  wwpLeosCfmExtFrameLossSessionFrameLossRatioFar OBJECT-TYPE
 	  SYNTAX			CfmFrameLossRatio
 	  MAX-ACCESS		read-only
 	  STATUS			current
 	  DESCRIPTION
 	     "This object specifies the Frame Loss Ratio in percentile of loss at Farend in the last iteration
              of the completed test."
 	  ::= { wwpLeosCfmExtFrameLossSessionEntry 26 } 
     
  wwpLeosCfmExtFrameLossSessionTxFCfStart OBJECT-TYPE
 	  SYNTAX			Unsigned32
 	  MAX-ACCESS		read-only
 	  STATUS			current
 	  DESCRIPTION
 	     "This object specifies the TxFCf counter of first received frame in the last iteration
              of the completed test."
 	  ::= { wwpLeosCfmExtFrameLossSessionEntry 27 } 
 	  
  wwpLeosCfmExtFrameLossSessionTxFCfEnd OBJECT-TYPE
 	  SYNTAX			Unsigned32
 	  MAX-ACCESS		read-only
 	  STATUS			current
 	  DESCRIPTION
 	     "This object specifies the TxFCf counter of last received frame in the last iteration
              of the completed test."
 	  ::= { wwpLeosCfmExtFrameLossSessionEntry 28 } 
 	  
  wwpLeosCfmExtFrameLossSessionRxFCfStart OBJECT-TYPE
 	  SYNTAX			Unsigned32
 	  MAX-ACCESS		read-only
 	  STATUS			current
 	  DESCRIPTION
 	     "This object specifies the RxFCf counter of first received frame in the last iteration
              of the completed test."
 	  ::= { wwpLeosCfmExtFrameLossSessionEntry 29 } 
 	  
  wwpLeosCfmExtFrameLossSessionRxFCfEnd OBJECT-TYPE
 	  SYNTAX			Unsigned32
 	  MAX-ACCESS		read-only
 	  STATUS			current
 	  DESCRIPTION
 	     "This object specifies the RxFCf counter of last received frame in the last iteration
              of the completed test."
 	  ::= { wwpLeosCfmExtFrameLossSessionEntry 30 } 
 	  
  wwpLeosCfmExtFrameLossSessionTxFCbStart OBJECT-TYPE
 	  SYNTAX			Unsigned32
 	  MAX-ACCESS		read-only
 	  STATUS			current
 	  DESCRIPTION
 	     "This object specifies the TxFCb counter of first received frame in the last iteration
              of the completed test."
 	  ::= { wwpLeosCfmExtFrameLossSessionEntry 31 } 
 	  
  wwpLeosCfmExtFrameLossSessionTxFCbEnd OBJECT-TYPE
 	  SYNTAX			Unsigned32
 	  MAX-ACCESS		read-only
 	  STATUS			current
 	  DESCRIPTION
 	     "This object specifies the TxFCb counter of last received frame in the last iteration
              of the completed test."
 	  ::= { wwpLeosCfmExtFrameLossSessionEntry 32 } 
 	  
  wwpLeosCfmExtFrameLossSessionRxFClStart OBJECT-TYPE
 	  SYNTAX			Unsigned32
 	  MAX-ACCESS		read-only
 	  STATUS			current
 	  DESCRIPTION
 	     "This object specifies the RxFCl counter while receiving the first frame in the last iteration
              of the completed test."
 	  ::= { wwpLeosCfmExtFrameLossSessionEntry 33 } 
 	  
  wwpLeosCfmExtFrameLossSessionRxFClEnd OBJECT-TYPE
 	  SYNTAX			Unsigned32
 	  MAX-ACCESS		read-only
 	  STATUS			current
 	  DESCRIPTION
 	     "This object specifies the RxFCl counter of while receiving the last frame in the last iteration
              of the completed test."
 	  ::= { wwpLeosCfmExtFrameLossSessionEntry 34 } 

  wwpLeosCfmExtFrameLossSessionConfigAccelerated	OBJECT-TYPE
 	 SYNTAX			TruthValue
 	 MAX-ACCESS		read-only
 	 STATUS			current
 	 DESCRIPTION
 	     "This object returns true if the measurement session is configured as a hardware accelerated." 
 	 ::= { wwpLeosCfmExtFrameLossSessionEntry 35 }    
 	 
   
 --
 -- LMM history multiple cos
 --
  wwpLeosCfmExtFrameLossSessionHistoryTable OBJECT-TYPE
     SYNTAX     	SEQUENCE OF WwpLeosCfmExtFrameLossSessionHistoryEntry
     MAX-ACCESS 	not-accessible
     STATUS     	current
     DESCRIPTION 	"The (conceptual) table listing the Y.1731 frame loss
     				History table for the CFM MEP."  
     ::= { wwpLeosCfmExtFrameLoss 3}   
     
  wwpLeosCfmExtFrameLossSessionHistoryEntry OBJECT-TYPE
     SYNTAX      	WwpLeosCfmExtFrameLossSessionHistoryEntry
     MAX-ACCESS  	not-accessible
     STATUS      	current
     DESCRIPTION    "An entry (conceptual row) in the wwpLeosCfmExtFrameLossSessionHistoryTable."
     INDEX {wwpLeosCfmServiceIndex, wwpLeosCfmExtMEPId,wwpLeosCfmRemoteMEPID,wwpLeosCfmExtFrameLossSessionTestId,
            wwpLeosCfmExtFrameLossSessionHistoryIndex}
     ::= { wwpLeosCfmExtFrameLossSessionHistoryTable 1 } 
       
  WwpLeosCfmExtFrameLossSessionHistoryEntry ::=  SEQUENCE {
     wwpLeosCfmExtFrameLossSessionHistoryIndex	                Unsigned32,      
     wwpLeosCfmExtFrameLossSessionHistoryServiceName            DisplayString,      
     wwpLeosCfmExtFrameLossSessionHistoryLocalMepid             Unsigned32,
     wwpLeosCfmExtFrameLossSessionHistoryLocalMacAddr           MacAddress,
     wwpLeosCfmExtFrameLossSessionHistoryRemoteMEPId            Unsigned32,
     wwpLeosCfmExtFrameLossSessionHistoryRemoteMacAddr          MacAddress,  	 
     wwpLeosCfmExtFrameLossSessionHistoryTestId                 Unsigned32,   
     wwpLeosCfmExtFrameLossSessionHistoryAccelerate             TruthValue,
     wwpLeosCfmExtFrameLossSessionHistoryPriority               Unsigned32,
     wwpLeosCfmExtFrameLossSessionHistoryIteration              Unsigned32,
     wwpLeosCfmExtFrameLossSessionHistoryLMMInterval            Unsigned32, 
     wwpLeosCfmExtFrameLossSessionHistoryNumLMMSent             Unsigned32,
     wwpLeosCfmExtFrameLossSessionHistoryNumLMRReceived	        Unsigned32,
     wwpLeosCfmExtFrameLossSessionHistoryFrameLossNear          Integer32,
     wwpLeosCfmExtFrameLossSessionHistoryFrameLossFar           Integer32,
     wwpLeosCfmExtFrameLossSessionHistoryMinFrameLossNear       Integer32,
     wwpLeosCfmExtFrameLossSessionHistoryMaxFrameLossNear       Integer32,
     wwpLeosCfmExtFrameLossSessionHistoryAvgFrameLossNear       Integer32, 
     wwpLeosCfmExtFrameLossSessionHistoryMinFrameLossFar        Integer32,
     wwpLeosCfmExtFrameLossSessionHistoryMaxFrameLossFar        Integer32,
     wwpLeosCfmExtFrameLossSessionHistoryAvgFrameLossFar        Integer32,  	 
     wwpLeosCfmExtFrameLossSessionHistoryLMMBadSequence	        Unsigned32,   	 
     wwpLeosCfmExtFrameLossSessionHistoryLMMMissedSequence      Unsigned32,
     wwpLeosCfmExtFrameLossSessionHistoryStartTime              Unsigned32,
     wwpLeosCfmExtFrameLossSessionHistoryStopTime               Unsigned32,
     wwpLeosCfmExtFrameLossSessionHistoryDuration               Unsigned32,
     wwpLeosCfmExtFrameLossSessionHistoryStatus	                INTEGER,
     wwpLeosCfmExtFrameLossSessionHistoryClear	                INTEGER,
     wwpLeosCfmExtFrameLossSessionHistoryFrameLossRatioNear     CfmFrameLossRatio,
     wwpLeosCfmExtFrameLossSessionHistoryFrameLossRatioFar      CfmFrameLossRatio,
     wwpLeosCfmExtFrameLossSessionHistoryTxFCfStart             Unsigned32,
     wwpLeosCfmExtFrameLossSessionHistoryTxFCfEnd               Unsigned32,
     wwpLeosCfmExtFrameLossSessionHistoryRxFCfStart             Unsigned32,
     wwpLeosCfmExtFrameLossSessionHistoryRxFCfEnd               Unsigned32,
     wwpLeosCfmExtFrameLossSessionHistoryTxFCbStart             Unsigned32,
     wwpLeosCfmExtFrameLossSessionHistoryTxFCbEnd               Unsigned32,
     wwpLeosCfmExtFrameLossSessionHistoryRxFClStart             Unsigned32,
     wwpLeosCfmExtFrameLossSessionHistoryRxFClEnd               Unsigned32
  }    
  
  wwpLeosCfmExtFrameLossSessionHistoryIndex OBJECT-TYPE
     SYNTAX      	Unsigned32 (1..256)
     MAX-ACCESS  	not-accessible
     STATUS      	current
     DESCRIPTION		"This is the history entry index into the table."
     ::= { wwpLeosCfmExtFrameLossSessionHistoryEntry 1 } 	   
    
  wwpLeosCfmExtFrameLossSessionHistoryServiceName OBJECT-TYPE
     SYNTAX       DisplayString (SIZE(1..31))
     MAX-ACCESS   read-only
     STATUS       current
     DESCRIPTION
             "This object identifies the CFM service name."
     ::= { wwpLeosCfmExtFrameLossSessionHistoryEntry 2 }  
      
  wwpLeosCfmExtFrameLossSessionHistoryLocalMepid OBJECT-TYPE
     SYNTAX      Unsigned32 
     MAX-ACCESS  read-only
     STATUS      current
     DESCRIPTION
             "This object identifies the local mepid."
     ::= { wwpLeosCfmExtFrameLossSessionHistoryEntry 3 }  
     
  wwpLeosCfmExtFrameLossSessionHistoryLocalMacAddr OBJECT-TYPE
     SYNTAX      MacAddress
     MAX-ACCESS  read-only
     STATUS      current
     DESCRIPTION
             "This object identifies the MAC address of the local mep. "
     ::= { wwpLeosCfmExtFrameLossSessionHistoryEntry 4 }    
     
 wwpLeosCfmExtFrameLossSessionHistoryRemoteMEPId OBJECT-TYPE
    SYNTAX      	Unsigned32 
    MAX-ACCESS  	read-only
    STATUS      	current
    DESCRIPTION    
              "This object identifies the remote mepid this test is run against."
    ::= { wwpLeosCfmExtFrameLossSessionHistoryEntry 5 }      
    
  wwpLeosCfmExtFrameLossSessionHistoryRemoteMacAddr OBJECT-TYPE
     SYNTAX      MacAddress
     MAX-ACCESS  read-only
     STATUS      current
     DESCRIPTION
          "This object identifies the MAC address of the remote mep."
     ::= { wwpLeosCfmExtFrameLossSessionHistoryEntry 6 }   
     
  wwpLeosCfmExtFrameLossSessionHistoryTestId OBJECT-TYPE
     SYNTAX       Unsigned32
     MAX-ACCESS   read-only
     STATUS       current
     DESCRIPTION
             "This object indicates test id to be
             used when sending link FrameLossMeasurementMsg."
     ::= { wwpLeosCfmExtFrameLossSessionHistoryEntry 7 }     
   
  wwpLeosCfmExtFrameLossSessionHistoryAccelerate OBJECT-TYPE
     SYNTAX       TruthValue
     MAX-ACCESS   read-only
     STATUS       current
     DESCRIPTION
             "This object specifies if the Loss session was accelerated or not."
     ::= { wwpLeosCfmExtFrameLossSessionHistoryEntry 8 }     

  wwpLeosCfmExtFrameLossSessionHistoryPriority OBJECT-TYPE
    SYNTAX      	Unsigned32 
    MAX-ACCESS  	read-only
    STATUS      	current
    DESCRIPTION
         "This object identifies the message priority of the Y.1731 LMM Frames sent on the given LMM test."  
    ::= { wwpLeosCfmExtFrameLossSessionHistoryEntry 9 }  
    
  wwpLeosCfmExtFrameLossSessionHistoryIteration  OBJECT-TYPE  
     SYNTAX       Unsigned32 
     MAX-ACCESS   read-only
     STATUS       current
     DESCRIPTION
             "This object indicates the iteration number of this session."
     ::= { wwpLeosCfmExtFrameLossSessionHistoryEntry 10 }  
    
  wwpLeosCfmExtFrameLossSessionHistoryLMMInterval OBJECT-TYPE
     SYNTAX      	Unsigned32 
     MAX-ACCESS  	read-only
     STATUS      	current
     DESCRIPTION  
             "This object identifies the LMM interval used to transmit the Y.1731 LMM Frames sent in this test."  
     ::= { wwpLeosCfmExtFrameLossSessionHistoryEntry 11 }  
         
  wwpLeosCfmExtFrameLossSessionHistoryNumLMMSent OBJECT-TYPE
 	 SYNTAX			Unsigned32
 	 MAX-ACCESS		read-only
 	 STATUS			current 
     DESCRIPTION	
    	     "This object specifies the number of LMM frames sent during the test iteration."
     ::= { wwpLeosCfmExtFrameLossSessionHistoryEntry 12 }  
    
  wwpLeosCfmExtFrameLossSessionHistoryNumLMRReceived OBJECT-TYPE
 	 SYNTAX			Unsigned32
 	 MAX-ACCESS		read-only
 	 STATUS			current 
     DESCRIPTION	
    	     "This object specifies the number of LMR frames received during the test iteration."
     ::= { wwpLeosCfmExtFrameLossSessionHistoryEntry 13 }  
    
  wwpLeosCfmExtFrameLossSessionHistoryFrameLossNear OBJECT-TYPE
 	  SYNTAX			Integer32 
 	  MAX-ACCESS		read-only
 	  STATUS			current
 	  DESCRIPTION
 	     "This object specifies the near loss result for this test iteration."
 	  ::= { wwpLeosCfmExtFrameLossSessionHistoryEntry 14 }
 	  
  wwpLeosCfmExtFrameLossSessionHistoryFrameLossFar OBJECT-TYPE
 	  SYNTAX			Integer32
 	  MAX-ACCESS		read-only
 	  STATUS			current
 	  DESCRIPTION
 	     "This object specifies the far loss result for this test iteration."
 	  ::= { wwpLeosCfmExtFrameLossSessionHistoryEntry 15 }

  wwpLeosCfmExtFrameLossSessionHistoryMinFrameLossNear OBJECT-TYPE
 	 SYNTAX			Integer32
 	 MAX-ACCESS		read-only
 	 STATUS			current 
     DESCRIPTION	
    	     "This object specifies the minimum frame loss near observed until this test iteration."
     ::= { wwpLeosCfmExtFrameLossSessionHistoryEntry 16 } 
     
  wwpLeosCfmExtFrameLossSessionHistoryMaxFrameLossNear OBJECT-TYPE
 	 SYNTAX			Integer32
 	 MAX-ACCESS		read-only
 	 STATUS			current 
     DESCRIPTION	
    	     "This object specifies the maximum frame loss near observed until this test iteration."
     ::= { wwpLeosCfmExtFrameLossSessionHistoryEntry 17 } 
    
  wwpLeosCfmExtFrameLossSessionHistoryAvgFrameLossNear OBJECT-TYPE
 	 SYNTAX			Integer32
 	 MAX-ACCESS		read-only
 	 STATUS			current 
     DESCRIPTION	
    	     "This object specifies the average frame loss near observed until this test iteration."
     ::= { wwpLeosCfmExtFrameLossSessionHistoryEntry 18 }   
    
  wwpLeosCfmExtFrameLossSessionHistoryMinFrameLossFar OBJECT-TYPE
 	 SYNTAX			Integer32
 	 MAX-ACCESS		read-only
 	 STATUS			current 
     DESCRIPTION	
    	     "This object specifies the minimum frame loss far observed until this test iteration."
     ::= { wwpLeosCfmExtFrameLossSessionHistoryEntry 19 }      
    
  wwpLeosCfmExtFrameLossSessionHistoryMaxFrameLossFar OBJECT-TYPE
 	 SYNTAX			Integer32
 	 MAX-ACCESS		read-only
 	 STATUS			current 
     DESCRIPTION	
    	     "This object specifies the maximum frame loss far observed until this test iteration."
     ::= { wwpLeosCfmExtFrameLossSessionHistoryEntry 20 }    
    
  wwpLeosCfmExtFrameLossSessionHistoryAvgFrameLossFar OBJECT-TYPE
 	 SYNTAX			Integer32
 	 MAX-ACCESS		read-only
 	 STATUS			current 
     DESCRIPTION	
    	     "This object specifies the average frame loss far observed until this test iteration."
     ::= { wwpLeosCfmExtFrameLossSessionHistoryEntry 21 } 
    
  wwpLeosCfmExtFrameLossSessionHistoryLMMBadSequence OBJECT-TYPE
 	 SYNTAX			Unsigned32
 	 MAX-ACCESS		read-only
 	 STATUS			current 
     DESCRIPTION	
    	     "This object specifies the number of frames with bad sequence numbers
 	          measured during the last LMM performance test on the given service and MEP."
     ::= { wwpLeosCfmExtFrameLossSessionHistoryEntry 22 }    
    
  wwpLeosCfmExtFrameLossSessionHistoryLMMMissedSequence OBJECT-TYPE
 	 SYNTAX			Unsigned32
 	 MAX-ACCESS		read-only
 	 STATUS			current 
     DESCRIPTION	
    	     "This object specifies the number of frames with missing sequence numbers
	     measured during the last LMM performance test iteration."
     ::= { wwpLeosCfmExtFrameLossSessionHistoryEntry 23 }  
    
  wwpLeosCfmExtFrameLossSessionHistoryStartTime OBJECT-TYPE
 	 SYNTAX			Unsigned32
 	 MAX-ACCESS		read-only
 	 STATUS			current
 	 DESCRIPTION	
 		     "This object specifies the time the test iteration started.
		     The timestamp is the number of seconds since 12AM Jan 1st, 1970."
 	 ::= { wwpLeosCfmExtFrameLossSessionHistoryEntry 24 }  
 	
  wwpLeosCfmExtFrameLossSessionHistoryStopTime OBJECT-TYPE
 	 SYNTAX			Unsigned32
 	 MAX-ACCESS		read-only
 	 STATUS			current                                   
 	 DESCRIPTION	
 		     "This object specifies the time the test terminated.
		     The timestamp is the number of seconds since 12AM Jan 1st, 1970."
 	::= { wwpLeosCfmExtFrameLossSessionHistoryEntry 25 }  
 	
  wwpLeosCfmExtFrameLossSessionHistoryDuration OBJECT-TYPE
 	 SYNTAX			Unsigned32
 	 MAX-ACCESS		read-only
 	 STATUS			current                                   
 	 DESCRIPTION
 		     "This object specifies the duration of time the test took to complete one iteration."
 	 ::= { wwpLeosCfmExtFrameLossSessionHistoryEntry 26 }  
 	
  wwpLeosCfmExtFrameLossSessionHistoryStatus OBJECT-TYPE
     SYNTAX      	INTEGER 
                    {
     					start(1),
     					done(2),
     					canceled(3),
     					timeout(4)
     				}
     MAX-ACCESS  	read-only
     STATUS      	current
     DESCRIPTION     
             "This object specifies the status of the test iteration.
             start - Test iteration transitions to this state once the test is started and in progress.
             done  - Test iteration transitions to this state once the test is completed.    
                     Transition to this state happens only after receiving all the responses and the timeout
                     if any is completed. 
             cancelled - Test iteration transitions to this state if the test was interrupted while it was running.
                         Such an interruption can happen if user explicitly  cancels the test or cfm/service was disabled. 
             timeout - Test session transitions to this state when all the messages were transmitted and has completed with errors. These 
                       errors can occur when the delay timeout has expired and not all responses were received."  
     ::= { wwpLeosCfmExtFrameLossSessionHistoryEntry 27 }  
    
  wwpLeosCfmExtFrameLossSessionHistoryClear OBJECT-TYPE
 	 SYNTAX 		INTEGER
 	                {
 					    none(0),
 						clear(1)
 					}
 	 MAX-ACCESS     read-write
 	 STATUS 		current
 	 DESCRIPTION 	
 	         "Setting this object to clear(1), clears MEP delay history for the
		 given service and MepId.  This object cannot be set to none."
 	 ::= { wwpLeosCfmExtFrameLossSessionHistoryEntry 28 } 
 	 
  wwpLeosCfmExtFrameLossSessionHistoryFrameLossRatioNear OBJECT-TYPE
 	 SYNTAX			CfmFrameLossRatio
 	 MAX-ACCESS		read-only
 	 STATUS			current                                   
 	 DESCRIPTION
 	     "This object specifies the Frame Loss Ratio in percentile of loss at Nearend."
 	 ::= { wwpLeosCfmExtFrameLossSessionHistoryEntry 29 }  
 	
  wwpLeosCfmExtFrameLossSessionHistoryFrameLossRatioFar OBJECT-TYPE
 	 SYNTAX			CfmFrameLossRatio
 	 MAX-ACCESS		read-only
 	 STATUS			current                                   
 	 DESCRIPTION
 	     "This object specifies the Frame Loss Ratio in percentile of loss at Farend."
 	 ::= { wwpLeosCfmExtFrameLossSessionHistoryEntry 30 }  
 	
  wwpLeosCfmExtFrameLossSessionHistoryTxFCfStart OBJECT-TYPE
 	 SYNTAX			Unsigned32
 	 MAX-ACCESS		read-only
 	 STATUS			current                                   
 	 DESCRIPTION
 	     "This object specifies the TxFCf counter of first received frame."
 	 ::= { wwpLeosCfmExtFrameLossSessionHistoryEntry 31 }  
 	
  wwpLeosCfmExtFrameLossSessionHistoryTxFCfEnd OBJECT-TYPE
 	 SYNTAX			Unsigned32
 	 MAX-ACCESS		read-only
 	 STATUS			current                                   
 	 DESCRIPTION
 	     "This object specifies the TxFCf counter of last received frame."
 	 ::= { wwpLeosCfmExtFrameLossSessionHistoryEntry 32 }  
 	
  wwpLeosCfmExtFrameLossSessionHistoryRxFCfStart OBJECT-TYPE
 	 SYNTAX			Unsigned32
 	 MAX-ACCESS		read-only
 	 STATUS			current                                   
 	 DESCRIPTION
 	     "This object specifies the RxFCf counter of first received frame."
 	 ::= { wwpLeosCfmExtFrameLossSessionHistoryEntry 33 }  
 	
  wwpLeosCfmExtFrameLossSessionHistoryRxFCfEnd OBJECT-TYPE
 	 SYNTAX			Unsigned32
 	 MAX-ACCESS		read-only
 	 STATUS			current                                   
 	 DESCRIPTION
 	     "This object specifies the RxFCf counter of last received frame."
 	 ::= { wwpLeosCfmExtFrameLossSessionHistoryEntry 34 }  
 	
  wwpLeosCfmExtFrameLossSessionHistoryTxFCbStart OBJECT-TYPE
 	 SYNTAX			Unsigned32
 	 MAX-ACCESS		read-only
 	 STATUS			current                                   
 	 DESCRIPTION
 	     "This object specifies the TxFCb counter of first received frame."
 	 ::= { wwpLeosCfmExtFrameLossSessionHistoryEntry 35 }  
 	
  wwpLeosCfmExtFrameLossSessionHistoryTxFCbEnd OBJECT-TYPE
 	 SYNTAX			Unsigned32
 	 MAX-ACCESS		read-only
 	 STATUS			current                                   
 	 DESCRIPTION
 	     "This object specifies the TxFCb counter of last received frame."
 	 ::= { wwpLeosCfmExtFrameLossSessionHistoryEntry 36 }  
 	
  wwpLeosCfmExtFrameLossSessionHistoryRxFClStart OBJECT-TYPE
 	 SYNTAX			Unsigned32
 	 MAX-ACCESS		read-only
 	 STATUS			current                                   
 	 DESCRIPTION
 	     "This object specifies the RxFCl counter while receiving the first frame."
 	 ::= { wwpLeosCfmExtFrameLossSessionHistoryEntry 37 }  
 	
  wwpLeosCfmExtFrameLossSessionHistoryRxFClEnd OBJECT-TYPE
 	 SYNTAX			Unsigned32
 	 MAX-ACCESS		read-only
 	 STATUS			current                                   
 	 DESCRIPTION
 	     "This object specifies the RxFCl counter of while receiving the last frame."
 	 ::= { wwpLeosCfmExtFrameLossSessionHistoryEntry 38 }  
  ---
  --- Frame Loss Responder Table
  ---
 	 
  wwpLeosCfmExtFrameLossResponderTable OBJECT-TYPE
     SYNTAX     SEQUENCE OF WwpLeosCfmExtFrameLossResponderEntry
     MAX-ACCESS not-accessible
     STATUS     current
     DESCRIPTION
            "The (conceptual) table lists the FrameLoss responders."
     ::= { wwpLeosCfmExtFrameLoss 4 }      
     
  wwpLeosCfmExtFrameLossResponderEntry OBJECT-TYPE
     SYNTAX      WwpLeosCfmExtFrameLossResponderEntry
     MAX-ACCESS  not-accessible
     STATUS      current
     DESCRIPTION
           "An entry (conceptual row) in the wwpLeosCfmExtFrameLossResponderTable."
     INDEX {wwpLeosCfmServiceIndex,
            wwpLeosCfmExtMEPId,
            wwpLeosCfmRemoteMEPID,
            wwpLeosCfmExtFrameLossResponderTestId }
     ::= { wwpLeosCfmExtFrameLossResponderTable 1 }  
     
  WwpLeosCfmExtFrameLossResponderEntry ::=  SEQUENCE {  
     wwpLeosCfmExtFrameLossResponderServiceName         DisplayString,
     wwpLeosCfmExtFrameLossResponderLocalMepId          Unsigned32,
     wwpLeosCfmExtFrameLossResponderLocalMac            MacAddress,     
	 wwpLeosCfmExtFrameLossResponderRemoteMepid         Unsigned32,
  	 wwpLeosCfmExtFrameLossResponderRemoteMac		    MacAddress,   
  	 wwpLeosCfmExtFrameLossResponderTestId              Unsigned32,
  	 wwpLeosCfmExtFrameLossResponderDataPriority        INTEGER,
     wwpLeosCfmExtFrameLossResponderAccelerated			TruthValue, 
     wwpLeosCfmExtFrameLossResponderNumLMMReceived      Unsigned32,
     wwpLeosCfmExtFrameLossResponderNumLMRSent          Unsigned32 	 
    } 
    
  wwpLeosCfmExtFrameLossResponderServiceName OBJECT-TYPE
     SYNTAX       DisplayString (SIZE(1..45))
     MAX-ACCESS   read-only
     STATUS       current
     DESCRIPTION
             "This object identifies the CFM service name."
     ::= { wwpLeosCfmExtFrameLossResponderEntry 1 }  
      
  wwpLeosCfmExtFrameLossResponderLocalMepId OBJECT-TYPE
     SYNTAX      Unsigned32
     MAX-ACCESS  read-only
     STATUS      current
     DESCRIPTION
             "This object identifies the local mepid."
     ::= { wwpLeosCfmExtFrameLossResponderEntry 2 } 
     
  wwpLeosCfmExtFrameLossResponderLocalMac OBJECT-TYPE
     SYNTAX      MacAddress
     MAX-ACCESS  read-only
     STATUS      current
     DESCRIPTION
             "This object identifies the MAC address of the local mep. "
     ::= { wwpLeosCfmExtFrameLossResponderEntry 3 }  
     
  wwpLeosCfmExtFrameLossResponderRemoteMepid OBJECT-TYPE
     SYNTAX      	Unsigned32 
     MAX-ACCESS  	read-only
     STATUS      	current
     DESCRIPTION    
             "This object identifies the remote mepid."
     ::= { wwpLeosCfmExtFrameLossResponderEntry 4 }   
    
  wwpLeosCfmExtFrameLossResponderRemoteMac OBJECT-TYPE
     SYNTAX      MacAddress
     MAX-ACCESS  read-only
     STATUS      current
     DESCRIPTION
             "This object identifies the MAC address of the remote mep."
     ::= { wwpLeosCfmExtFrameLossResponderEntry 5 } 
     
  wwpLeosCfmExtFrameLossResponderTestId OBJECT-TYPE
     SYNTAX      Unsigned32
     MAX-ACCESS  not-accessible
     STATUS      current
     DESCRIPTION
             "This object identifies the Test Id of the session."
     ::= { wwpLeosCfmExtFrameLossResponderEntry 6 }
     
  wwpLeosCfmExtFrameLossResponderDataPriority OBJECT-TYPE
     SYNTAX      INTEGER 
 	                {  zero(0),
 	                   one(1),
 	                   two(2),
 	                   three(3),
 	                   four(4),
 	                   five(5),
 	                   six(6),
 	                   seven(7),
 	                   all(8)
 	                }
     MAX-ACCESS  read-only
     STATUS      current
     DESCRIPTION
             "This object identifies the DOT1 Data priority of the data packet."
     ::= { wwpLeosCfmExtFrameLossResponderEntry 7 }   
     
  wwpLeosCfmExtFrameLossResponderAccelerated OBJECT-TYPE
     SYNTAX      TruthValue
     MAX-ACCESS  read-only
     STATUS      current
     DESCRIPTION
             "This object identifies if the responder is hardware accelerated or not.
              True if Hardware assisted, False if not. "
     ::= { wwpLeosCfmExtFrameLossResponderEntry 8 }
     
  wwpLeosCfmExtFrameLossResponderNumLMMReceived OBJECT-TYPE
     SYNTAX      Unsigned32
     MAX-ACCESS  read-only
     STATUS      current
     DESCRIPTION
             "This object specifies the number of LMM received by this responder." 
     ::= { wwpLeosCfmExtFrameLossResponderEntry 9 } 
     
  wwpLeosCfmExtFrameLossResponderNumLMRSent OBJECT-TYPE
     SYNTAX      Unsigned32
     MAX-ACCESS  read-only
     STATUS      current
     DESCRIPTION
             "This object specifies the number of LMR sent by this responder." 
     ::= { wwpLeosCfmExtFrameLossResponderEntry 10 }
   
 --
  --  CFM EXT Port Stack Table
  --                                   
 wwpLeosCfmExtInterfaceStackTable OBJECT-TYPE
     SYNTAX     SEQUENCE OF WwpLeosCfmExtInterfaceStackEntry
     MAX-ACCESS not-accessible
     STATUS     current
     DESCRIPTION
            "The (conceptual) table listing the display
             parameters for the CFM port stack table."
     ::= { wwpLeosCfmExtInterfaceStack 1 }
                
 wwpLeosCfmExtInterfaceStackEntry OBJECT-TYPE
     SYNTAX      WwpLeosCfmExtInterfaceStackEntry
     MAX-ACCESS  not-accessible
     STATUS      current
     DESCRIPTION
           "An entry (conceptual row) in the wwpLeosTceCfmPortStackTable."
     INDEX {wwpLeosCfmExtInterfaceStackServiceInstanceType,
            wwpLeosCfmExtInterfaceStackServiceInstanceIndex,
            wwpLeosCfmExtInterfaceStackInterfaceType,
            wwpLeosCfmExtInterfaceStackInterfaceIndex,                        
            wwpLeosCfmExtInterfaceStackStackType,
            wwpLeosCfmExtInterfaceStackLevel            
            }
     ::= { wwpLeosCfmExtInterfaceStackTable 1 }
                
 WwpLeosCfmExtInterfaceStackEntry ::=  SEQUENCE {
  wwpLeosCfmExtInterfaceStackServiceInstanceType           INTEGER,
  wwpLeosCfmExtInterfaceStackServiceInstanceIndex          Unsigned32,
  wwpLeosCfmExtInterfaceStackInterfaceType                 INTEGER,
  wwpLeosCfmExtInterfaceStackInterfaceIndex                Unsigned32,
  wwpLeosCfmExtInterfaceStackLevel                         Unsigned32,
  wwpLeosCfmExtInterfaceStackStackType                     INTEGER,
  wwpLeosCfmExtInterfaceStackInterfaceName                 DisplayString,
  wwpLeosCfmExtInterfaceStackServiceInstanceName           DisplayString,    
  wwpLeosCfmExtInterfaceStackPortName                      DisplayString,
  wwpLeosCfmExtInterfaceStackOperState                     INTEGER, 
  wwpLeosCfmExtInterfaceStackVid                           INTEGER,
  wwpLeosCfmExtInterfaceStackPgid                          Unsigned32,
  wwpLeosCfmExtInterfaceStackMEPId                         INTEGER,
  wwpLeosCfmExtInterfaceStackMacAddress                    MacAddress
  }                           

 wwpLeosCfmExtInterfaceStackServiceInstanceType OBJECT-TYPE
     SYNTAX      INTEGER  {
                           ethVs(1),
                           vlan(2),
                           pbtTunnel(3)                                 
     }
     MAX-ACCESS  not-accessible
     STATUS      current
     DESCRIPTION
             "This object specifies the CFM port service type."
     ::= { wwpLeosCfmExtInterfaceStackEntry 1 }
 
 wwpLeosCfmExtInterfaceStackServiceInstanceIndex OBJECT-TYPE
     SYNTAX      Unsigned32 (1..65535) 
     MAX-ACCESS  not-accessible
     STATUS      current
     DESCRIPTION
             "This object specifies a unique identifier for CFM domain entry."
     ::= { wwpLeosCfmExtInterfaceStackEntry 2 }


 wwpLeosCfmExtInterfaceStackInterfaceType OBJECT-TYPE
     SYNTAX      INTEGER  {
                                logicalPort(1),
                                pbtEncap(2),
                                pbtDecap(3),
                                none(99)
     }
     MAX-ACCESS  not-accessible
     STATUS      current
     DESCRIPTION
             "This object specifies the CFM interface type."
     ::= { wwpLeosCfmExtInterfaceStackEntry 3 }

 wwpLeosCfmExtInterfaceStackInterfaceIndex  OBJECT-TYPE
     SYNTAX      Unsigned32
     MAX-ACCESS  not-accessible
     STATUS      current
     DESCRIPTION
             "This object specifies the CFM sub port index."
     ::= { wwpLeosCfmExtInterfaceStackEntry 4 }
 
 wwpLeosCfmExtInterfaceStackLevel   OBJECT-TYPE
     SYNTAX      Unsigned32     (0..7)
     MAX-ACCESS  not-accessible
     STATUS      current
     DESCRIPTION
             "This object specifies the CFM interface level."
     ::= { wwpLeosCfmExtInterfaceStackEntry 5 }
 
 wwpLeosCfmExtInterfaceStackStackType    OBJECT-TYPE
     SYNTAX      INTEGER        {
                                        mepUp(1),
                                        mepDown(2),
                                        mipUp(3),
                                        mipDown(4)
     }
     MAX-ACCESS  not-accessible
     STATUS      current
     DESCRIPTION
             "This object specifies the CFM interface type."
     ::= { wwpLeosCfmExtInterfaceStackEntry 6 }
 
 wwpLeosCfmExtInterfaceStackInterfaceName    OBJECT-TYPE
     SYNTAX      DisplayString (SIZE(0..31))
     MAX-ACCESS  read-only
     STATUS      current
     DESCRIPTION
             "This object specifies the CFM interface name."
     ::= { wwpLeosCfmExtInterfaceStackEntry 7 }

 wwpLeosCfmExtInterfaceStackServiceInstanceName    OBJECT-TYPE
     SYNTAX      DisplayString (SIZE(0..31))
     MAX-ACCESS  read-only
     STATUS      current
     DESCRIPTION
             "This object specifies the CFM service interface name."
     ::= { wwpLeosCfmExtInterfaceStackEntry 8 }
 
 wwpLeosCfmExtInterfaceStackPortName    OBJECT-TYPE
     SYNTAX      DisplayString (SIZE(0..31))
     MAX-ACCESS  read-only
     STATUS      current
     DESCRIPTION
             "This object specifies the CFM interface port name."
     ::= { wwpLeosCfmExtInterfaceStackEntry 9 }
 
 wwpLeosCfmExtInterfaceStackOperState    OBJECT-TYPE
     SYNTAX      INTEGER        {
                                        up(1),
                                        down(2)
     }
     MAX-ACCESS  read-only
     STATUS      current
     DESCRIPTION
             "This object specifies the CFM interface oper state."
     ::= { wwpLeosCfmExtInterfaceStackEntry 10 }
 
 wwpLeosCfmExtInterfaceStackVid    OBJECT-TYPE
     SYNTAX      INTEGER (0..4094)
     MAX-ACCESS  read-only
     STATUS      current
     DESCRIPTION
             "This object specifies the CFM interface vid."
     ::= { wwpLeosCfmExtInterfaceStackEntry 11 }
 
 wwpLeosCfmExtInterfaceStackPgid     OBJECT-TYPE
     SYNTAX      Unsigned32
     MAX-ACCESS  read-only
     STATUS      current
     DESCRIPTION
             "This object specifies the CFM interface pgid."
     ::= { wwpLeosCfmExtInterfaceStackEntry 12 }

 wwpLeosCfmExtInterfaceStackMEPId      OBJECT-TYPE
     SYNTAX      INTEGER  (1..8191)
     MAX-ACCESS  read-only
     STATUS      current
     DESCRIPTION
             "This object specifies the CFM interface mepid."
     ::= { wwpLeosCfmExtInterfaceStackEntry 13 }
 
 wwpLeosCfmExtInterfaceStackMacAddress      OBJECT-TYPE
     SYNTAX      MacAddress
     MAX-ACCESS  read-only
     STATUS      current
     DESCRIPTION
             "This object specifies the CFM interface MAC address."
     ::= { wwpLeosCfmExtInterfaceStackEntry 14 }                           

 --
 -- CFM EXT MIP Table
 --                          
 wwpLeosCfmExtMipTable OBJECT-TYPE
     SYNTAX     SEQUENCE OF WwpLeosCfmExtMipEntry
     MAX-ACCESS not-accessible
     STATUS     current
     DESCRIPTION
            "The (conceptual) table listing the configuration
            parameters for the CFM Ext MIP Table.
            This table is not applicable if wwpLeosCfmServiceType is set to pbtTunnel.
            Any Get/Set/Walk returns an error."
     ::= { wwpLeosCfmExtMIP 1 }
                
 wwpLeosCfmExtMipEntry OBJECT-TYPE
     SYNTAX      WwpLeosCfmExtMipEntry
     MAX-ACCESS  not-accessible
     STATUS      current
     DESCRIPTION
           "An entry (conceptual row) in the wwpLeosCfmExtMipTable."
     INDEX {wwpLeosCfmExtMipVid, wwpLeosCfmExtMipPort, wwpLeosCfmExtMipLevel}
     ::= { wwpLeosCfmExtMipTable 1 }
                
 WwpLeosCfmExtMipEntry ::=  SEQUENCE { 
     wwpLeosCfmExtMipVid                        INTEGER,
     wwpLeosCfmExtMipPort                       INTEGER,
     wwpLeosCfmExtMipLevel                      INTEGER,
     wwpLeosCfmExtMipStatus                     RowStatus
 }

 wwpLeosCfmExtMipVid OBJECT-TYPE
     SYNTAX      INTEGER (0..24576)
     MAX-ACCESS  not-accessible
     STATUS      current
     DESCRIPTION
             "This object is used as index in the table and specifies the
              VLAN service type for which intermediate maintenance points can be created."
     ::= { wwpLeosCfmExtMipEntry 1 }
 
 wwpLeosCfmExtMipPort OBJECT-TYPE
     SYNTAX      INTEGER (1..65535)
     MAX-ACCESS  not-accessible
     STATUS      current
     DESCRIPTION
             "This object is used as index in the table and specifies the port."
     ::= { wwpLeosCfmExtMipEntry 2 }
                    
 wwpLeosCfmExtMipLevel OBJECT-TYPE
     SYNTAX       INTEGER (0..7)
     MAX-ACCESS   not-accessible
     STATUS       current
     DESCRIPTION
             "This object specifies the level attribute."
     ::= { wwpLeosCfmExtMipEntry 3 }

 wwpLeosCfmExtMipStatus OBJECT-TYPE
     SYNTAX       RowStatus
     MAX-ACCESS   read-create
     STATUS       current
     DESCRIPTION
             "Used to manage the creation and deletion of the conceptual rows in this table.
	     To create a row in this table, set this object to 'createAndGo'.
	     To delete a row in this table, set it to 'destroy'."
     ::= { wwpLeosCfmExtMipEntry 4 }

 --
 -- CFM EXT Interface MIP Table
 --                          
 wwpLeosCfmExtInterfaceMipTable OBJECT-TYPE
     SYNTAX     SEQUENCE OF WwpLeosCfmExtInterfaceMipEntry
     MAX-ACCESS not-accessible
     STATUS     current
     DESCRIPTION
            "The (conceptual) table listing the configuration
            parameters for the CFM Ext MIP SI Table."
     ::= { wwpLeosCfmExtInterfaceMIP 1 }
                
 wwpLeosCfmExtInterfaceMipEntry OBJECT-TYPE
     SYNTAX      WwpLeosCfmExtInterfaceMipEntry
     MAX-ACCESS  not-accessible
     STATUS      current
     DESCRIPTION
           "An entry (conceptual row) in the wwpLeosCfmExtInterfaceMipTable."
     INDEX {wwpLeosCfmExtInterfaceMipServiceInstanceType,
            wwpLeosCfmExtInterfaceMipServiceInstanceIndex,
            wwpLeosCfmExtInterfaceMipInterfaceType,
            wwpLeosCfmExtInterfaceMipInterfaceIndex,
            wwpLeosCfmExtInterfaceMipInterfaceSubIndex,
            wwpLeosCfmExtInterfaceMipLevel}
     ::= { wwpLeosCfmExtInterfaceMipTable 1 }
                
 WwpLeosCfmExtInterfaceMipEntry ::=  SEQUENCE { 
     wwpLeosCfmExtInterfaceMipServiceInstanceType   INTEGER,
     wwpLeosCfmExtInterfaceMipServiceInstanceIndex  Unsigned32,
     wwpLeosCfmExtInterfaceMipInterfaceType         INTEGER,
     wwpLeosCfmExtInterfaceMipInterfaceIndex        Unsigned32,
     wwpLeosCfmExtInterfaceMipInterfaceSubIndex     Unsigned32,
     wwpLeosCfmExtInterfaceMipLevel                 INTEGER,
     wwpLeosCfmExtInterfaceMipStatus                RowStatus
 }

 wwpLeosCfmExtInterfaceMipServiceInstanceType OBJECT-TYPE
     SYNTAX      INTEGER  {
                           ethVs(1),
                           vlan(2),
                           pbtTunnel(3)                                 
     }
     MAX-ACCESS  not-accessible
     STATUS      current
     DESCRIPTION
             "This object specifies the service instance type.
              Interpretation of wwpLeosCfmExtInterfaceMipServiceInstanceIndex depends on the value of this MIB object."
     ::= { wwpLeosCfmExtInterfaceMipEntry 1 }
 
 wwpLeosCfmExtInterfaceMipServiceInstanceIndex OBJECT-TYPE
     SYNTAX      Unsigned32 (1..65535) 
     MAX-ACCESS  not-accessible
     STATUS      current
     DESCRIPTION
             "This object specifies the service instance index.
              Interpretation of this object depends on the value of wwpLeosCfmExtInterfaceMipServiceInstanceType."
     ::= { wwpLeosCfmExtInterfaceMipEntry 2 }

 wwpLeosCfmExtInterfaceMipInterfaceType OBJECT-TYPE
     SYNTAX      INTEGER  {
                                none(0),
                                portVlan(1),
                                pbtEncap(2),
                                pbtDecap(3)
     }
     MAX-ACCESS  not-accessible
     STATUS      current
     DESCRIPTION
             "This object specifies the CFM interface type."
     ::= { wwpLeosCfmExtInterfaceMipEntry 3 }

 wwpLeosCfmExtInterfaceMipInterfaceIndex  OBJECT-TYPE
     SYNTAX      Unsigned32
     MAX-ACCESS  not-accessible
     STATUS      current
     DESCRIPTION
             "This object specifies an interface index.
              When the value of object wwpLeosCfmExtInterfaceMipInterfaceType
              is portVlan this obect refers to a port."
     ::= { wwpLeosCfmExtInterfaceMipEntry 4 }

 wwpLeosCfmExtInterfaceMipInterfaceSubIndex  OBJECT-TYPE
     SYNTAX      Unsigned32
     MAX-ACCESS  not-accessible
     STATUS      current
     DESCRIPTION
             "This object specifies a sub interface index.
              When the value of object wwpLeosCfmExtInterfaceMipInterfaceType
              is portVlan this obect refers to a vlan."
     ::= { wwpLeosCfmExtInterfaceMipEntry 5 }                    

 wwpLeosCfmExtInterfaceMipLevel OBJECT-TYPE
     SYNTAX       INTEGER (0..7)
     MAX-ACCESS   not-accessible
     STATUS       current
     DESCRIPTION
             "This object specifies the level attribute."
     ::= { wwpLeosCfmExtInterfaceMipEntry 6 }

 wwpLeosCfmExtInterfaceMipStatus OBJECT-TYPE
     SYNTAX       RowStatus
     MAX-ACCESS   read-create
     STATUS       current
     DESCRIPTION
             "Used to manage the creation and deletion of the conceptual rows in this table.
	     To create a row in this table, set this object to 'createAndGo'.
	     To delete a row in this table, set it to 'destroy'."
     ::= { wwpLeosCfmExtInterfaceMipEntry 7 }

  --
  --  CFM OAM Port Table
  --                                   
 wwpLeosCfmExtOamPortTable OBJECT-TYPE
     SYNTAX     SEQUENCE OF WwpLeosCfmExtOamPortEntry
     MAX-ACCESS not-accessible
     STATUS     current
     DESCRIPTION
            "The (conceptual) table listing  if a port is OAM capable."
     ::= { wwpLeosCfmExtOamPort 1 }
                
 wwpLeosCfmExtOamPortEntry OBJECT-TYPE
     SYNTAX      WwpLeosCfmExtOamPortEntry
     MAX-ACCESS  not-accessible
     STATUS      current
     DESCRIPTION
           "An entry (conceptual row) in the wwpLeosCfmExtOamPortTable."
     INDEX {wwpLeosCfmExtOamPortIndex }
     ::= { wwpLeosCfmExtOamPortTable 1 }
                
 WwpLeosCfmExtOamPortEntry ::=  SEQUENCE {
  wwpLeosCfmExtOamPortIndex                Integer32,
  wwpLeosCfmExtOamPortSupported            TruthValue,
  wwpLeosCfmExtOamPortHwY1731DmmSupported  TruthValue,
  wwpLeosCfmExtOamPortHwY1731LmmSupported  TruthValue
  }                           

 wwpLeosCfmExtOamPortIndex OBJECT-TYPE
     SYNTAX      Integer32  (1..3072)
     MAX-ACCESS  not-accessible
     STATUS      current
     DESCRIPTION
             "This object specifies the port index."
     ::= { wwpLeosCfmExtOamPortEntry 1 }
 
 wwpLeosCfmExtOamPortSupported OBJECT-TYPE
     SYNTAX      TruthValue 
     MAX-ACCESS  read-only
     STATUS      current
     DESCRIPTION
             "This object specifies if the port is OAM capable."
     ::= { wwpLeosCfmExtOamPortEntry 2 } 
     
  wwpLeosCfmExtOamPortHwY1731DmmSupported OBJECT-TYPE
     SYNTAX      TruthValue 
     MAX-ACCESS  read-only
     STATUS      current
     DESCRIPTION
             "This object specifies if the port is Hardware Y1731 Delay measurement capable."
     ::= { wwpLeosCfmExtOamPortEntry 3 }
     
   wwpLeosCfmExtOamPortHwY1731LmmSupported OBJECT-TYPE
     SYNTAX      TruthValue 
     MAX-ACCESS  read-only
     STATUS      current
     DESCRIPTION
             "This object specifies if the port is Hardware Y1731 Loss measurement capable."
     ::= { wwpLeosCfmExtOamPortEntry 4 }
  
  --
  --  CFM Synthetic Loss Measurement Msg Table
  --
  wwpLeosCfmExtSynLossSessionTable OBJECT-TYPE
  	  SYNTAX     SEQUENCE OF WwpLeosCfmExtSynLossSessionEntry
  	  MAX-ACCESS not-accessible
      STATUS     current
      DESCRIPTION
            "The (conceptual) table listing the configuration
            parameters for the SyntheticLossMeasurementMsg."
     ::= { wwpLeosCfmExtSynLoss 1 }    
     
  wwpLeosCfmExtSynLossSessionEntry OBJECT-TYPE   
      SYNTAX     WwpLeosCfmExtSynLossSessionEntry   
  	  MAX-ACCESS not-accessible
      STATUS     current
      DESCRIPTION
           "An entry in the wwpLeosCfmExtMultipleCoSSynLossMsgTable.
           To send, clear or cancel the message, the corresponding MsgAction
           needs to be specified. Individual objects in this table
           cannot be set. To send or cancel a message, the TargetMepID or the
           TargtetMacAddr objects need to be specified.
           Clear msgAction clears the counters for the message."
      INDEX {
             wwpLeosCfmServiceIndex,
             wwpLeosCfmExtMEPId,
             wwpLeosCfmRemoteMEPID,
             wwpLeosCfmExtSynLossSessionTestId
            }
     ::= { wwpLeosCfmExtSynLossSessionTable 1 }       
     
  WwpLeosCfmExtSynLossSessionEntry ::= SEQUENCE { 
       wwpLeosCfmExtSynLossSessionTestId                    Unsigned32,
       wwpLeosCfmExtSynLossSessionPriority                  Unsigned32,
       wwpLeosCfmExtSynLossSessionCount                     Unsigned32,
       wwpLeosCfmExtSynLossSessionSLMInterval               Unsigned32,  
       wwpLeosCfmExtSynLossSessionIterations                Unsigned32,
       wwpLeosCfmExtSynLossSessionRepeatDelay               Unsigned32,
       wwpLeosCfmExtSynLossSessionFrameSize                 Unsigned32,      
       wwpLeosCfmExtSynLossSessionTimeout                   Unsigned32,
       wwpLeosCfmExtSynLossSessionDuration                  Unsigned32,
       wwpLeosCfmExtSynLossSessionAction                    SendState,
       wwpLeosCfmExtSynLossSessionFlnThreshold              Integer32,
       wwpLeosCfmExtSynLossSessionFlfThreshold              Integer32,
       wwpLeosCfmExtSynLossSessionNumSLMSent                Unsigned32,
       wwpLeosCfmExtSynLossSessionNumSLRReceived            Unsigned32,
       wwpLeosCfmExtSynLossSessionFrameLossNear             Integer32,
       wwpLeosCfmExtSynLossSessionFrameLossFar              Integer32,
       wwpLeosCfmExtSynLossSessionAvgFrameLossNear          Integer32,
       wwpLeosCfmExtSynLossSessionMinFrameLossNear          Integer32,
       wwpLeosCfmExtSynLossSessionMaxFrameLossNear          Integer32,
       wwpLeosCfmExtSynLossSessionAvgFrameLossFar           Integer32,
       wwpLeosCfmExtSynLossSessionMinFrameLossFar           Integer32,
       wwpLeosCfmExtSynLossSessionMaxFrameLossFar           Integer32,
       wwpLeosCfmExtSynLossSessionFrameLossRatioNear        CfmFrameLossRatio,
       wwpLeosCfmExtSynLossSessionFrameLossRatioFar         CfmFrameLossRatio,
       wwpLeosCfmExtSynLossSessionTxFCfStart                Unsigned32,
       wwpLeosCfmExtSynLossSessionTxFCfEnd                  Unsigned32,
       wwpLeosCfmExtSynLossSessionTxFCbStart                Unsigned32,
       wwpLeosCfmExtSynLossSessionTxFCbEnd                  Unsigned32,
       wwpLeosCfmExtSynLossSessionRxFClStart                Unsigned32,
       wwpLeosCfmExtSynLossSessionRxFClEnd                  Unsigned32,
       wwpLeosCfmExtSynLossSessionAccelerated               TruthValue, 
       wwpLeosCfmExtSynLossSessionConfigAccelerated         TruthValue,
       wwpLeosCfmExtSynLossSessionFrameDeliveryRatio        CfmFrameRatio,
       wwpLeosCfmExtSynLossSessionSuspect                   TruthValue,
       wwpLeosCfmExtSynLossSessionSdSetThreshold            Integer32,
       wwpLeosCfmExtSynLossSessionSdClearThreshold          Integer32,
       wwpLeosCfmExtSynLossSessionTwoWayFrameLoss           Integer32,
       wwpLeosCfmExtSynLossSessionTwoWayFrameLossRatio      CfmFrameRatio

  } 
   
  wwpLeosCfmExtSynLossSessionTestId  OBJECT-TYPE
      SYNTAX 	   Unsigned32 (1..4294967295)
  	  MAX-ACCESS   not-accessible
      STATUS       current      
      DESCRIPTION
      		  "This object specifies the test ID of the SLM message."
      ::= { wwpLeosCfmExtSynLossSessionEntry 1 }
      
  wwpLeosCfmExtSynLossSessionPriority  OBJECT-TYPE  
     SYNTAX       Unsigned32 (0..7)
     MAX-ACCESS   read-create
     STATUS       current
     DESCRIPTION
             "This object specifies the SLM Msg priority to be used
              when sending link SyntheticLossMeasurementMsg."
     ::= { wwpLeosCfmExtSynLossSessionEntry 2 } 
     
  wwpLeosCfmExtSynLossSessionCount  OBJECT-TYPE
      SYNTAX       Unsigned32 (0 | 2..65535) 
      MAX-ACCESS   read-create
      STATUS       current
      DESCRIPTION
             "This object specifies the SLM Msg count to be used
              when sending link SyntheticLossMeasurementMsg. When this object is set
              to zero, the CFM Global default is applied."
     ::= { wwpLeosCfmExtSynLossSessionEntry 3 }
     
  wwpLeosCfmExtSynLossSessionSLMInterval  OBJECT-TYPE
     SYNTAX       Unsigned32 (0 | 2..7)
     MAX-ACCESS   read-create
     STATUS       current
     DESCRIPTION
             "This object specifies the SLM Msg interval to be used
              when sending link SyntheticLossMeasurementMsg.
	      If set to Zero, CFM global default interval setting is applied.
              
              The values 2-7 represent indices to CFM CCM intervals as follows:
              2 --> 10ms,
              3 --> 100ms,
              4 --> 1sec,
              5 --> 10sec,
              6 --> 1min,
              7 --> 10min."
     ::= { wwpLeosCfmExtSynLossSessionEntry 4 }      
     
  wwpLeosCfmExtSynLossSessionIterations  OBJECT-TYPE  
     SYNTAX       Unsigned32 (0..60)
     MAX-ACCESS   read-create
     STATUS       current
     DESCRIPTION
             "This object specifies the number of iterations the test
              has to be conducted. Each test iteration is defined by wwpLeosCfmExtSynLossMsgSLMInterval,
              wwpLeosCfmExtSynLossMsgCount. Whereas, the test sessions is defined by test iterations over 
              wwpLeosCfmExtSynLossMsgRepeatCount.
              
              If this object is set to zero, it means that test is continuous, and iterations are infinite. "
     ::= { wwpLeosCfmExtSynLossSessionEntry 5 }     
          
  wwpLeosCfmExtSynLossSessionRepeatDelay  OBJECT-TYPE  
     SYNTAX       Unsigned32 (0..1440)
     MAX-ACCESS   read-create
     STATUS       current
     DESCRIPTION
             "This object specifies the delay in minutes between consecutive test iterations."
     ::= { wwpLeosCfmExtSynLossSessionEntry 6 } 
     
  wwpLeosCfmExtSynLossSessionFrameSize  OBJECT-TYPE  
     SYNTAX       Unsigned32 (0 | 65..1400)
     MAX-ACCESS   read-create
     STATUS       current
     DESCRIPTION
             "This object specifies the size in bytes of the CFM Base frame.
              If this object is set to zero there is NO padding."
     ::= { wwpLeosCfmExtSynLossSessionEntry 7 }   
       
  wwpLeosCfmExtSynLossSessionTimeout  OBJECT-TYPE  
     SYNTAX       Unsigned32 (0 | 2000..10000)
     MAX-ACCESS   read-create
     STATUS       current
     DESCRIPTION
             "This object specifies the timeout interval in milliseconds within which
              the source should Rx a SLR for a corresponding SLM Msg.
              If this object is set to zero, the CFM global default setting is applied."
     ::= { wwpLeosCfmExtSynLossSessionEntry 8 }
       
  wwpLeosCfmExtSynLossSessionDuration OBJECT-TYPE
	  SYNTAX	  Unsigned32 (0..65535)
	  MAX-ACCESS  read-create
	  STATUS	  current                                   
	  DESCRIPTION
	   "This object specifies the duration of time the test took in milliseconds to complete one iteration."
	  ::= { wwpLeosCfmExtSynLossSessionEntry 9 }
   
  wwpLeosCfmExtSynLossSessionAction OBJECT-TYPE
     SYNTAX       SendState
     MAX-ACCESS   read-create
     STATUS       current
     DESCRIPTION
             "This object represents the action for the message (send, clear or cancel)
             This object represents the action for the message (send, clear or cancel)
             If set to send(1) and if wwpLeosCfmExtSynLossSessionTargetMEPID is specified
             then FrameLossMsg is sent to remote mepid.
             Setting to clear(2) clears mep statistics for given service and mepid.
             If set to cancel(3) and if wwpLeosCfmExtSynLossSessionTargetMEPID is specified
             then it cancels sending FrameLoss messages to remoteMEPID."
     ::= { wwpLeosCfmExtSynLossSessionEntry 10 }  
     
  wwpLeosCfmExtSynLossSessionFlnThreshold OBJECT-TYPE
 	  SYNTAX			Integer32 (-1..65535)
 	  MAX-ACCESS		read-create
 	  STATUS			current
 	  DESCRIPTION
	 		  "This object represents the Near Loss Threshold Fault for the Frame Loss Measurement test.
	 		   A value of -1 disables the generation of faults.  A value of 0 or greater
	 		   is compared to the frame loss near result of the
	 		   test and a fault is generated if the threshold is exceeded."
 	  ::= { wwpLeosCfmExtSynLossSessionEntry 11 }  
 	
  wwpLeosCfmExtSynLossSessionFlfThreshold OBJECT-TYPE
 	  SYNTAX			Integer32 (-1..65535)
 	  MAX-ACCESS		read-create
 	  STATUS			current
 	  DESCRIPTION
 			  "This object represents the Far Loss Threshold Fault for the Frame Loss Measurement test.
 			   A value of -1 disables the generation of faults. A value of 0 or greater
 			   is compared to the frame loss near result of the
 			   test and a fault is generated if the threshold is exceeded."
 	  ::= { wwpLeosCfmExtSynLossSessionEntry 12 }          
  
  wwpLeosCfmExtSynLossSessionNumSLMSent OBJECT-TYPE
 	  SYNTAX			Unsigned32 (1..65535)
 	  MAX-ACCESS		read-only
 	  STATUS			current
 	  DESCRIPTION
 	     "This object specifies the number of SLM sent in the last iteration of the completed test."
 	  ::= { wwpLeosCfmExtSynLossSessionEntry 13 }

   wwpLeosCfmExtSynLossSessionNumSLRReceived OBJECT-TYPE
 	  SYNTAX			Unsigned32 (1..65535)
 	  MAX-ACCESS		read-only
 	  STATUS			current
 	  DESCRIPTION
 	      "This object specifies the number of SLR received in the last iteration of the completed test."
 	  ::= { wwpLeosCfmExtSynLossSessionEntry 14 }
 	  
  wwpLeosCfmExtSynLossSessionFrameLossNear OBJECT-TYPE
 	  SYNTAX			Integer32 
 	  MAX-ACCESS		read-only
 	  STATUS			current
 	  DESCRIPTION
 	    "This object specifies the Near Loss Threshold in the last iteration of the completed test."
 	  ::= { wwpLeosCfmExtSynLossSessionEntry 15 }
 	  
  wwpLeosCfmExtSynLossSessionFrameLossFar OBJECT-TYPE
 	  SYNTAX			Integer32
 	  MAX-ACCESS		read-only
 	  STATUS			current
 	  DESCRIPTION
 	    "This object specifies the Far Loss Threshold in the last iteration of the completed test."
 	  ::= { wwpLeosCfmExtSynLossSessionEntry 16 }
 	  
  wwpLeosCfmExtSynLossSessionAvgFrameLossNear OBJECT-TYPE
 	  SYNTAX			Integer32 
 	  MAX-ACCESS		read-only
 	  STATUS			current
 	  DESCRIPTION
 		  "This object specifies the average Near Loss Threshold in the last iteration of the completed test."
 	  ::= { wwpLeosCfmExtSynLossSessionEntry 17 }
 	  
  wwpLeosCfmExtSynLossSessionMinFrameLossNear OBJECT-TYPE
 	  SYNTAX			Integer32 
 	  MAX-ACCESS		read-only
 	  STATUS			current
 	  DESCRIPTION
 		 "This object specifies the minimum Near Loss Threshold in the last iteration of the completed test."
 	  ::= { wwpLeosCfmExtSynLossSessionEntry 18 }
 	  
  wwpLeosCfmExtSynLossSessionMaxFrameLossNear OBJECT-TYPE
 	  SYNTAX			Integer32 
 	  MAX-ACCESS		read-only
 	  STATUS			current
 	  DESCRIPTION
 		"This object specifies the maximum Near Loss Threshold in the last iteration of the completed test."
 	  ::= { wwpLeosCfmExtSynLossSessionEntry 19 }
 	  
  wwpLeosCfmExtSynLossSessionAvgFrameLossFar OBJECT-TYPE
 	  SYNTAX			Integer32 
 	  MAX-ACCESS		read-only
 	  STATUS			current
 	  DESCRIPTION
 	   "This object specifies the average Far Loss Thrsshold in the last iteration of the completed test."
 	  ::= { wwpLeosCfmExtSynLossSessionEntry 20 }
 	  
  wwpLeosCfmExtSynLossSessionMinFrameLossFar OBJECT-TYPE
 	  SYNTAX			Integer32 
 	  MAX-ACCESS		read-only
 	  STATUS			current
 	  DESCRIPTION
 	     "This object specifies the minimum Far Loss Threshold in the last iteration of the completed test."
 	  ::= { wwpLeosCfmExtSynLossSessionEntry 21 }
 	  
  wwpLeosCfmExtSynLossSessionMaxFrameLossFar OBJECT-TYPE
 	  SYNTAX			Integer32 
 	  MAX-ACCESS		read-only
 	  STATUS			current
 	  DESCRIPTION
 	     "This object specifies the maximum Far Loss Threshold in the last iteration of the completed test."
 	  ::= { wwpLeosCfmExtSynLossSessionEntry 22 } 

  wwpLeosCfmExtSynLossSessionFrameLossRatioNear OBJECT-TYPE
          SYNTAX          CfmFrameLossRatio
          MAX-ACCESS      read-only
          STATUS          current
          DESCRIPTION
             "This object specifies the Frame Loss Ratio in percentile of loss at Nearend in the last 
              iteration of the completed test."
          ::= { wwpLeosCfmExtSynLossSessionEntry 23 } 
 
  wwpLeosCfmExtSynLossSessionFrameLossRatioFar OBJECT-TYPE
          SYNTAX          CfmFrameLossRatio
          MAX-ACCESS      read-only
          STATUS          current
          DESCRIPTION
             "This object specifies the Frame Loss Ratio in percentile of loss at Farend in the last 
              iteration of the completed test."
          ::= { wwpLeosCfmExtSynLossSessionEntry 24 } 
 
  wwpLeosCfmExtSynLossSessionTxFCfStart OBJECT-TYPE
          SYNTAX          Unsigned32
          MAX-ACCESS      read-only
          STATUS          current
          DESCRIPTION
             "This object specifies the txFCf counter in the first received test frame in the last 
              iteration of the completed test."
          ::= { wwpLeosCfmExtSynLossSessionEntry 25 } 
 
  wwpLeosCfmExtSynLossSessionTxFCfEnd OBJECT-TYPE
          SYNTAX          Unsigned32
          MAX-ACCESS      read-only
          STATUS          current
          DESCRIPTION
             "This object specifies the txFCf counter in the last received test frame in the last 
              iteration of the completed test."
          ::= { wwpLeosCfmExtSynLossSessionEntry 26 } 
 
  wwpLeosCfmExtSynLossSessionTxFCbStart OBJECT-TYPE
          SYNTAX          Unsigned32
          MAX-ACCESS      read-only
          STATUS          current
          DESCRIPTION
             "This object specifies the txFCb counter in the first received test frame in the last 
              iteration of the completed test."
          ::= { wwpLeosCfmExtSynLossSessionEntry 27 } 
 
  wwpLeosCfmExtSynLossSessionTxFCbEnd OBJECT-TYPE
          SYNTAX          Unsigned32
          MAX-ACCESS      read-only
          STATUS          current
          DESCRIPTION
             "This object specifies the txFCb counter in the last received test frame in the last 
              iteration of the completed test."
          ::= { wwpLeosCfmExtSynLossSessionEntry 28 } 
 
  wwpLeosCfmExtSynLossSessionRxFClStart OBJECT-TYPE
          SYNTAX          Unsigned32
          MAX-ACCESS      read-only
          STATUS          current
          DESCRIPTION
             "This object specifies the RxFCl counter while receiving the first test frame in the last 
              iteration of the completed test."
          ::= { wwpLeosCfmExtSynLossSessionEntry 29 } 
 
  wwpLeosCfmExtSynLossSessionRxFClEnd OBJECT-TYPE
          SYNTAX          Unsigned32
          MAX-ACCESS      read-only
          STATUS          current
          DESCRIPTION
             "This object specifies the RxFCl counter while receiving the last test frame in the last 
              iteration of the completed test."
          ::= { wwpLeosCfmExtSynLossSessionEntry 30 } 
 	  
  wwpLeosCfmExtSynLossSessionAccelerated	OBJECT-TYPE
 	 SYNTAX			TruthValue
 	 MAX-ACCESS		read-create
 	 STATUS			current
 	 DESCRIPTION
 	     "Setting this attribute to true gathers synthetic loss measurements in hardware. 
             This object returns true if synthetic loss sender is actively utilizing hardware resources."
 	 ::= { wwpLeosCfmExtSynLossSessionEntry 31 }    
 	 
  wwpLeosCfmExtSynLossSessionConfigAccelerated	OBJECT-TYPE
 	 SYNTAX			TruthValue
 	 MAX-ACCESS		read-only
 	 STATUS			current
 	 DESCRIPTION
 	     "This object returns true if the measurement session is configured as a hardware accelerated." 
 	 ::= { wwpLeosCfmExtSynLossSessionEntry 32 }    

  wwpLeosCfmExtSynLossSessionFrameDeliveryRatio	OBJECT-TYPE
 	 SYNTAX			CfmFrameRatio
 	 MAX-ACCESS		read-only
 	 STATUS			current
 	 DESCRIPTION
 	     "This object specifies the Frame Delivery Ratio as percentage of total number of SLR frames received
              divided by total number of SLM frames sent in the last iteration of the completed test."
 	 ::= { wwpLeosCfmExtSynLossSessionEntry 33 } 

  wwpLeosCfmExtSynLossSessionSuspect	OBJECT-TYPE
 	 SYNTAX			TruthValue
 	 MAX-ACCESS		read-only
 	 STATUS			current
 	 DESCRIPTION
 	     "This object indicates that there is discontinuity in SLM Performance Measurement.
 	      Condition for discontinuity include:
 	      a) The conducting of performance measurement is halted before the current measurement interval is completed."
 	 ::= { wwpLeosCfmExtSynLossSessionEntry 34 } 
 	 
  wwpLeosCfmExtSynLossSessionSdSetThreshold OBJECT-TYPE
 	 SYNTAX                 Integer32 (-1 | 1..65535)
 	 MAX-ACCESS             read-create
 	 STATUS                 current
 	 DESCRIPTION
             "This object represents the signal degrade set threshold value for the synthetic loss measurement test.
              A value of 1 or greater is compared to the frame loss result and fault is set, if the loss exceeds
              this threshold. A value of -1 disables the generation of signal degrade fault notification.
              This object works in conjunction with wwpLeosCfmExtSynLossSessionSdClearThreshold. If one object is given 
              non-default value, other should be also set to non-default value."
 	 DEFVAL {-1}
 	 ::= { wwpLeosCfmExtSynLossSessionEntry 35 }  
  
 wwpLeosCfmExtSynLossSessionSdClearThreshold OBJECT-TYPE
 	 SYNTAX                 Integer32 (-1..65534)
 	 MAX-ACCESS             read-create
 	 STATUS                 current
 	 DESCRIPTION
             "This object represents the signal degrade clear threshold value for the synthetic loss measurement test.
              A value of 0 or greater is compared to the frame loss result and a fault is cleared, if loss 
              is equal to or below this threshold. A value of -1 disables the generation of signal degrade fault notification
              This object works in conjunction with wwpLeosCfmExtSynLossSessionSdSetThreshold. If one object is given 
              non-default value, other should be also set to non-default value."
 	 DEFVAL {-1}
 	 ::= { wwpLeosCfmExtSynLossSessionEntry 36 }

 wwpLeosCfmExtSynLossSessionTwoWayFrameLoss OBJECT-TYPE
 	 SYNTAX                 Integer32
 	 MAX-ACCESS             read-only
 	 STATUS                 current
 	 DESCRIPTION
             "This object specifies the number of lost frames for the round trip measured in the last iteration of the
              complete test."
 	 ::= { wwpLeosCfmExtSynLossSessionEntry 37 }

 wwpLeosCfmExtSynLossSessionTwoWayFrameLossRatio OBJECT-TYPE
 	 SYNTAX                 CfmFrameRatio
 	 MAX-ACCESS             read-only
 	 STATUS                 current
 	 DESCRIPTION
             "This object specifies the Frame Loss Ratio as percentage of difference of SLM frames sent and SLR 
              frames received divided by total number of SLM frames sent in the last iteration of the completed test."
 	 ::= { wwpLeosCfmExtSynLossSessionEntry 38 }

  ---
  ---  CFM Synthetic Loss Measurement History Table
  ---
  wwpLeosCfmExtSynLossSessionHistoryTable OBJECT-TYPE
     SYNTAX     SEQUENCE OF WwpLeosCfmExtSynLossSessionHistoryEntry
     MAX-ACCESS not-accessible
     STATUS     current
     DESCRIPTION
            "The (conceptual) table listing the history of
             test iterations in a session."  
     ::= { wwpLeosCfmExtSynLoss 2 }

  wwpLeosCfmExtSynLossSessionHistoryEntry OBJECT-TYPE   
      SYNTAX     WwpLeosCfmExtSynLossSessionHistoryEntry   
  	  MAX-ACCESS not-accessible
      STATUS     current
      DESCRIPTION
           "An entry (conceptual row) in the wwpLeosCfmExtSynLossResultHistoryTable."
      INDEX {
             wwpLeosCfmServiceIndex, 
             wwpLeosCfmExtMEPId, 
             wwpLeosCfmRemoteMEPID, 
             wwpLeosCfmExtSynLossSessionTestId, 
             wwpLeosCfmExtSynLossSessionHistoryIndex
            }
     ::= { wwpLeosCfmExtSynLossSessionHistoryTable 1 }
	 	                                           
  WwpLeosCfmExtSynLossSessionHistoryEntry ::= SEQUENCE {                                                 
    wwpLeosCfmExtSynLossSessionHistoryIndex                           Integer32,
    wwpLeosCfmExtSynLossSessionHistoryServiceName                     DisplayString,
    wwpLeosCfmExtSynLossSessionHistoryLocalMepid                      Unsigned32,
    wwpLeosCfmExtSynLossSessionHistoryRemoteMepid                     Unsigned32,
    wwpLeosCfmExtSynLossSessionHistoryTestId                          Unsigned32,
    wwpLeosCfmExtSynLossSessionHistoryPriority                        Integer32,
    wwpLeosCfmExtSynLossSessionHistoryIteration                       Unsigned32,
    wwpLeosCfmExtSynLossSessionHistorySLMInterval                     Integer32,
    wwpLeosCfmExtSynLossSessionHistoryFrameSize                       Unsigned32, 
    wwpLeosCfmExtSynLossSessionHistoryNumSLMSent                      Unsigned32,
    wwpLeosCfmExtSynLossSessionHistoryNumSLRReceived                  Unsigned32,
    wwpLeosCfmExtSynLossSessionHistoryFrameLossNear                   Integer32,
    wwpLeosCfmExtSynLossSessionHistoryFrameLossFar                    Integer32,
    wwpLeosCfmExtSynLossSessionHistoryAvgFrameLossNear                Integer32,
    wwpLeosCfmExtSynLossSessionHistoryMinFrameLossNear                Integer32,
    wwpLeosCfmExtSynLossSessionHistoryMaxFrameLossNear                Integer32,
    wwpLeosCfmExtSynLossSessionHistoryAvgFrameLossFar                 Integer32,
    wwpLeosCfmExtSynLossSessionHistoryMinFrameLossFar                 Integer32,
    wwpLeosCfmExtSynLossSessionHistoryMaxFrameLossFar                 Integer32,   
    wwpLeosCfmExtSynLossSessionHistoryStartTime                       Unsigned32,
    wwpLeosCfmExtSynLossSessionHistoryStopTime                        Unsigned32,
    wwpLeosCfmExtSynLossSessionHistoryDuration                        Unsigned32,
    wwpLeosCfmExtSynLossSessionHistoryStatus                          INTEGER,
    wwpLeosCfmExtSynLossSessionHistoryClear                           INTEGER,
    wwpLeosCfmExtSynLossSessionHistoryRemoteMacAddr                   MacAddress,
    wwpLeosCfmExtSynLossSessionHistoryFrameLossRatioNear              CfmFrameLossRatio,
    wwpLeosCfmExtSynLossSessionHistoryFrameLossRatioFar               CfmFrameLossRatio,
    wwpLeosCfmExtSynLossSessionHistoryTxFCfStart                      Unsigned32,
    wwpLeosCfmExtSynLossSessionHistoryTxFCfEnd                        Unsigned32,
    wwpLeosCfmExtSynLossSessionHistoryTxFCbStart                      Unsigned32,
    wwpLeosCfmExtSynLossSessionHistoryTxFCbEnd                        Unsigned32,
    wwpLeosCfmExtSynLossSessionHistoryRxFClStart                      Unsigned32,
    wwpLeosCfmExtSynLossSessionHistoryRxFClEnd                        Unsigned32,
    wwpLeosCfmExtSynLossSessionHistoryFrameDeliveryRatio              CfmFrameRatio,
    wwpLeosCfmExtSynLossSessionHistorySuspect                         TruthValue,
    wwpLeosCfmExtSynLossSessionHistorySignalDegradeStatus             TruthValue,
    wwpLeosCfmExtSynLossSessionHistorySignalDegradeSuspect            TruthValue,
    wwpLeosCfmExtSynLossSessionHistoryTwoWayFrameLoss                 Integer32,
    wwpLeosCfmExtSynLossSessionHistoryTwoWayFrameLossRatio            CfmFrameRatio
  } 
  
  wwpLeosCfmExtSynLossSessionHistoryIndex OBJECT-TYPE
        SYNTAX          Integer32 (0..255)
        MAX-ACCESS      not-accessible
        STATUS          current
        DESCRIPTION     "This is the history entry index into the table."
        ::= { wwpLeosCfmExtSynLossSessionHistoryEntry 1 }  
        
  
   wwpLeosCfmExtSynLossSessionHistoryServiceName OBJECT-TYPE
        SYNTAX          DisplayString (SIZE(1..31))
        MAX-ACCESS      read-only
        STATUS          current
        DESCRIPTION
                 "This object identifies the CFM service name."
        ::= { wwpLeosCfmExtSynLossSessionHistoryEntry 2 }   
    
   wwpLeosCfmExtSynLossSessionHistoryLocalMepid OBJECT-TYPE
        SYNTAX          Unsigned32 (1..8191)
        MAX-ACCESS      read-only
        STATUS          current
        DESCRIPTION
                "This object identifies the local mepid."
        ::= { wwpLeosCfmExtSynLossSessionHistoryEntry 3 }   
         
   wwpLeosCfmExtSynLossSessionHistoryRemoteMepid OBJECT-TYPE
        SYNTAX      Unsigned32 (1..8191)
        MAX-ACCESS  read-only
        STATUS      current
        DESCRIPTION
                "This object identifies the local mepid."
        ::= { wwpLeosCfmExtSynLossSessionHistoryEntry 4 }  
        
   wwpLeosCfmExtSynLossSessionHistoryTestId  OBJECT-TYPE
        SYNTAX       Unsigned32 (1..4294967295)
        MAX-ACCESS   read-only
        STATUS       current      
        DESCRIPTION
                "This object specifies the test ID of the SLM message."
        ::= { wwpLeosCfmExtSynLossSessionHistoryEntry 5 }
        
  wwpLeosCfmExtSynLossSessionHistoryPriority  OBJECT-TYPE  
         SYNTAX       Integer32 (0..7)
         MAX-ACCESS   read-only
         STATUS       current
         DESCRIPTION
                 "This object specifies the SLM Msg priority to be used
                  when sending link SyntheticLossMeasurementMsg."
         ::= { wwpLeosCfmExtSynLossSessionHistoryEntry 6 }

  wwpLeosCfmExtSynLossSessionHistoryIteration  OBJECT-TYPE  
        SYNTAX       Unsigned32 
        MAX-ACCESS   read-only
        STATUS       current
        DESCRIPTION
                 "This object indicates the iteration number of this session."
        ::= { wwpLeosCfmExtSynLossSessionHistoryEntry 7 }
                 
  wwpLeosCfmExtSynLossSessionHistorySLMInterval  OBJECT-TYPE
         SYNTAX       Integer32 (1..7)
         MAX-ACCESS   read-only
         STATUS       current
         DESCRIPTION
                 "This object specifies the SLM Msg interval to be used
                  when sending link SyntheticLossMeasurementMsg."
         ::= { wwpLeosCfmExtSynLossSessionHistoryEntry 8 }

   wwpLeosCfmExtSynLossSessionHistoryFrameSize  OBJECT-TYPE  
         SYNTAX       Unsigned32 (0 | 47..1400)
         MAX-ACCESS   read-only      
         STATUS       current
         DESCRIPTION
                 "This object specifies the size in bytes of the CFM Base frame."
         ::= { wwpLeosCfmExtSynLossSessionHistoryEntry 9 }
         
   wwpLeosCfmExtSynLossSessionHistoryNumSLMSent OBJECT-TYPE
          SYNTAX            Unsigned32 (1..65535)
          MAX-ACCESS    read-only
          STATUS            current
          DESCRIPTION
                  "This object specifies the number of SLM sent in this test iteration."
          ::= { wwpLeosCfmExtSynLossSessionHistoryEntry 10 }

          
   wwpLeosCfmExtSynLossSessionHistoryNumSLRReceived OBJECT-TYPE
          SYNTAX            Unsigned32 (1..65535)
          MAX-ACCESS    read-only
          STATUS            current
          DESCRIPTION
                  "This object specifies the number of SLR received in this test iteration."
          ::= { wwpLeosCfmExtSynLossSessionHistoryEntry 11 }  
    
   wwpLeosCfmExtSynLossSessionHistoryFrameLossNear OBJECT-TYPE
          SYNTAX            Integer32 
          MAX-ACCESS    read-only
          STATUS            current
          DESCRIPTION
                  "This object specifies the Near Loss in this test iteration."
          ::= { wwpLeosCfmExtSynLossSessionHistoryEntry 12 }
          
   wwpLeosCfmExtSynLossSessionHistoryFrameLossFar OBJECT-TYPE
          SYNTAX            Integer32 
          MAX-ACCESS    read-only
          STATUS            current
          DESCRIPTION
                  "This object specifies the Far Loss in this iteration."
          ::= { wwpLeosCfmExtSynLossSessionHistoryEntry 13 } 
          
          
   wwpLeosCfmExtSynLossSessionHistoryAvgFrameLossNear OBJECT-TYPE
          SYNTAX            Integer32
          MAX-ACCESS    read-only
          STATUS            current
          DESCRIPTION
                  "This object specifies the Average Near Loss in this iteration."
          ::= { wwpLeosCfmExtSynLossSessionHistoryEntry 14 }
          
   wwpLeosCfmExtSynLossSessionHistoryMinFrameLossNear OBJECT-TYPE
          SYNTAX            Integer32 
          MAX-ACCESS    read-only
          STATUS            current
          DESCRIPTION
                  "This object specifies the minimum Near Loss in this iteration."
          ::= { wwpLeosCfmExtSynLossSessionHistoryEntry 15 } 
          
   wwpLeosCfmExtSynLossSessionHistoryMaxFrameLossNear OBJECT-TYPE
          SYNTAX            Integer32 
          MAX-ACCESS    read-only
          STATUS            current
          DESCRIPTION
                  "This object specifies the maximum Near Loss in this iteration."
          ::= { wwpLeosCfmExtSynLossSessionHistoryEntry 16 }
          
   wwpLeosCfmExtSynLossSessionHistoryAvgFrameLossFar OBJECT-TYPE
          SYNTAX            Integer32 
          MAX-ACCESS    read-only
          STATUS            current
          DESCRIPTION
                  "This object specifies the average Far Loss in this iteration."
          ::= { wwpLeosCfmExtSynLossSessionHistoryEntry 17 }
          
   wwpLeosCfmExtSynLossSessionHistoryMinFrameLossFar OBJECT-TYPE
          SYNTAX            Integer32 
          MAX-ACCESS    read-only
          STATUS            current
          DESCRIPTION
                  "This object specifies the minimum Far Loss in this iteration."
          ::= { wwpLeosCfmExtSynLossSessionHistoryEntry 18 }

   wwpLeosCfmExtSynLossSessionHistoryMaxFrameLossFar OBJECT-TYPE
          SYNTAX            Integer32 
          MAX-ACCESS    read-only
          STATUS            current
          DESCRIPTION
                  "This object specifies the maximum Far Loss in this iteration."
          ::= { wwpLeosCfmExtSynLossSessionHistoryEntry 19 }  

   wwpLeosCfmExtSynLossSessionHistoryStartTime OBJECT-TYPE
          SYNTAX            Unsigned32
          MAX-ACCESS    read-only
          STATUS            current
          DESCRIPTION   
                  "This object specifies the time the test iteration started.
		  The timestamp is the number of seconds since 12AM Jan 1st, 1970."
          ::= { wwpLeosCfmExtSynLossSessionHistoryEntry 20 }
 
   wwpLeosCfmExtSynLossSessionHistoryStopTime OBJECT-TYPE
          SYNTAX               Unsigned32
          MAX-ACCESS      read-only
          STATUS              current                                   
          DESCRIPTION   
                  "This object specifies the time the test terminated.
		  The timestamp is the number of seconds since 12AM Jan 1st, 1970."
          ::= { wwpLeosCfmExtSynLossSessionHistoryEntry 21 }   
          
   wwpLeosCfmExtSynLossSessionHistoryDuration OBJECT-TYPE
         SYNTAX             Unsigned32
         MAX-ACCESS    read-only
         STATUS            current                                   
         DESCRIPTION
                "This object specifies the duration of time the test took in milliseconds
		to complete one iteration."
         ::= { wwpLeosCfmExtSynLossSessionHistoryEntry 22 }
          
   wwpLeosCfmExtSynLossSessionHistoryStatus OBJECT-TYPE
          SYNTAX             INTEGER {
                            running(1),  --deprecated
                            done(2),
                            canceled(3),
                            timeout(4),
                            start(5)
                         }
          MAX-ACCESS     read-only
          STATUS             current
          DESCRIPTION    
             "This object specifies the status of the test iteration.
             start - Test iteration transitions to this state once the test is started and in progress.
             done  - Test iteration transitions to this state once the test is completed.    
                     Transition to this state happens only after receiving all the responses and the timeout
                     if any is completed. 
             cancelled - Test iteration transitions to this state if the test was interrupted while it was running.
                         Such an interruption can happen if user explicitly  cancels the test or cfm/service was disabled. 
             timeout - Test session transitions to this state when all the messages were transmitted and has completed with errors. These 
                       errors can occur when the delay timeout has expired and not all responses were received."  
          ::= { wwpLeosCfmExtSynLossSessionHistoryEntry 23 }
                      
   wwpLeosCfmExtSynLossSessionHistoryClear OBJECT-TYPE
         SYNTAX             INTEGER {
                                none(0),
                                clear(1)
                            }
         MAX-ACCESS    read-write
         STATUS             current
         DESCRIPTION    
                  "Setting this object to clear(1), clears MEP Synthetic Loss history for the
                   given service and MepId.  This object cannot be set to none."
         ::= { wwpLeosCfmExtSynLossSessionHistoryEntry 24 } 
         
   wwpLeosCfmExtSynLossSessionHistoryRemoteMacAddr OBJECT-TYPE
         SYNTAX      MacAddress
         MAX-ACCESS  read-only
         STATUS      current
         DESCRIPTION
                  "This object identifies the MAC address of the remote mep."
         ::= { wwpLeosCfmExtSynLossSessionHistoryEntry 25 }

   wwpLeosCfmExtSynLossSessionHistoryFrameLossRatioNear OBJECT-TYPE
         SYNTAX       CfmFrameLossRatio
         MAX-ACCESS   read-only
         STATUS       current
         DESCRIPTION
                  "This object specifies the Frame Loss Ratio in percentile of loss at Nearend."
         ::= { wwpLeosCfmExtSynLossSessionHistoryEntry 26 } 
 
   wwpLeosCfmExtSynLossSessionHistoryFrameLossRatioFar OBJECT-TYPE
         SYNTAX       CfmFrameLossRatio
         MAX-ACCESS   read-only
         STATUS       current
         DESCRIPTION
                  "This object specifies the Frame Loss Ratio in percentile of loss at Farend."
         ::= { wwpLeosCfmExtSynLossSessionHistoryEntry 27 } 
 	  
   wwpLeosCfmExtSynLossSessionHistoryTxFCfStart OBJECT-TYPE
         SYNTAX       Unsigned32
         MAX-ACCESS   read-only
         STATUS       current
         DESCRIPTION
                  "This object specifies the TxFCf counter in the first received test frame."
         ::= { wwpLeosCfmExtSynLossSessionHistoryEntry 28 } 

   wwpLeosCfmExtSynLossSessionHistoryTxFCfEnd OBJECT-TYPE
         SYNTAX       Unsigned32
         MAX-ACCESS   read-only
         STATUS       current
         DESCRIPTION
                  "This object specifies the TxFCf counter in the last received test frame."
         ::= { wwpLeosCfmExtSynLossSessionHistoryEntry 29 } 

   wwpLeosCfmExtSynLossSessionHistoryTxFCbStart OBJECT-TYPE
         SYNTAX       Unsigned32
         MAX-ACCESS   read-only
         STATUS       current
         DESCRIPTION
                  "This object specifies the TxFCb counter in the first received test frame."
         ::= { wwpLeosCfmExtSynLossSessionHistoryEntry 30 } 

   wwpLeosCfmExtSynLossSessionHistoryTxFCbEnd OBJECT-TYPE
         SYNTAX       Unsigned32
         MAX-ACCESS   read-only
         STATUS       current
         DESCRIPTION
                  "This object specifies the TxFCb counter in the last received test frame."
         ::= { wwpLeosCfmExtSynLossSessionHistoryEntry 31 } 

   wwpLeosCfmExtSynLossSessionHistoryRxFClStart OBJECT-TYPE
         SYNTAX       Unsigned32
         MAX-ACCESS   read-only
         STATUS       current
         DESCRIPTION
                  "This object specifies the RxFCl counter while receiving the first test frame."
         ::= { wwpLeosCfmExtSynLossSessionHistoryEntry 32 } 

   wwpLeosCfmExtSynLossSessionHistoryRxFClEnd OBJECT-TYPE
         SYNTAX       Unsigned32
         MAX-ACCESS   read-only
         STATUS       current
         DESCRIPTION
                  "This object specifies the RxFCl counter while receiving the last test frame."
         ::= { wwpLeosCfmExtSynLossSessionHistoryEntry 33 } 

   wwpLeosCfmExtSynLossSessionHistoryFrameDeliveryRatio OBJECT-TYPE
         SYNTAX          CfmFrameRatio
         MAX-ACCESS      read-only
         STATUS          current
         DESCRIPTION
                  "This object specifies the Frame Delivery Ratio as percentage of total number of SLR frames received
                   divided by total number of SLM frames sent."
         ::= { wwpLeosCfmExtSynLossSessionHistoryEntry 34 }

    wwpLeosCfmExtSynLossSessionHistorySuspect OBJECT-TYPE
         SYNTAX          TruthValue
         MAX-ACCESS      read-only
         STATUS          current
         DESCRIPTION
                  "This object indicates that there was discontinuity in SLM Performance Measurement.
                   Condition for discontinuity include:
                   a) The conducting of performance measurement is halted before the current measurement interval is completed."
         ::= { wwpLeosCfmExtSynLossSessionHistoryEntry 35 } 

    wwpLeosCfmExtSynLossSessionHistorySignalDegradeStatus OBJECT-TYPE
         SYNTAX          TruthValue
         MAX-ACCESS      read-only
         STATUS          current
         DESCRIPTION
                  "This object specifies the degrade status in this iteration."
         ::= { wwpLeosCfmExtSynLossSessionHistoryEntry 36 } 
   
    wwpLeosCfmExtSynLossSessionHistorySignalDegradeSuspect OBJECT-TYPE
         SYNTAX          TruthValue
         MAX-ACCESS      read-only
         STATUS          current
         DESCRIPTION
                  "This object indicates that there was discontinuity in signal degrade monitoring in this iteration.
                   Condition for discontinuity include:
                   a) There is link flapping in this iteration.
                   b) Link is operationally down in this iteration."
         ::= { wwpLeosCfmExtSynLossSessionHistoryEntry 37 } 

    wwpLeosCfmExtSynLossSessionHistoryTwoWayFrameLoss OBJECT-TYPE
         SYNTAX          Integer32 
         MAX-ACCESS      read-only
         STATUS          current
         DESCRIPTION
                  "This object specifies the number of lost frames for the round trip measured in this iteration."
         ::= { wwpLeosCfmExtSynLossSessionHistoryEntry 38 } 

    wwpLeosCfmExtSynLossSessionHistoryTwoWayFrameLossRatio OBJECT-TYPE
         SYNTAX          CfmFrameRatio
         MAX-ACCESS      read-only
         STATUS          current
         DESCRIPTION
                  "This object specifies the Frame Loss Ratio as percentage of difference of SLM frames sent and SLR
                   frames received divided by total number of SLM frames sent in this iteration."
         ::= { wwpLeosCfmExtSynLossSessionHistoryEntry 39 } 

  ---
  --- Synthetic Loss Responder Table
  ---
 	 
  wwpLeosCfmExtSynLossResponderTable OBJECT-TYPE
     SYNTAX     SEQUENCE OF WwpLeosCfmExtSynLossResponderEntry
     MAX-ACCESS not-accessible
     STATUS     current
     DESCRIPTION
            "The (conceptual) table lists the SynLoss responders."
     ::= { wwpLeosCfmExtSynLoss 3 }      
     
  wwpLeosCfmExtSynLossResponderEntry OBJECT-TYPE
     SYNTAX      WwpLeosCfmExtSynLossResponderEntry
     MAX-ACCESS  not-accessible
     STATUS      current
     DESCRIPTION
           "An entry (conceptual row) in the wwpLeosCfmExtSynLossResponderTable."
     INDEX {wwpLeosCfmServiceIndex,
            wwpLeosCfmExtMEPId,
            wwpLeosCfmRemoteMEPID,
            wwpLeosCfmExtSynLossResponderTestId }
     ::= { wwpLeosCfmExtSynLossResponderTable 1 }  
     
  WwpLeosCfmExtSynLossResponderEntry ::=  SEQUENCE {  
     wwpLeosCfmExtSynLossResponderTestId              Unsigned32,
     wwpLeosCfmExtSynLossResponderServiceName         DisplayString,
     wwpLeosCfmExtSynLossResponderLocalMepId          Unsigned32,
     wwpLeosCfmExtSynLossResponderLocalMac            MacAddress,     
     wwpLeosCfmExtSynLossResponderRemoteMepid         Unsigned32,
     wwpLeosCfmExtSynLossResponderRemoteMac           MacAddress,   
     wwpLeosCfmExtSynLossResponderAccelerated         TruthValue, 
     wwpLeosCfmExtSynLossResponderNumSLMReceived      Unsigned32,
     wwpLeosCfmExtSynLossResponderNumSLRSent          Unsigned32 	 
    } 
    
  wwpLeosCfmExtSynLossResponderTestId OBJECT-TYPE
     SYNTAX      Unsigned32
     MAX-ACCESS  not-accessible
     STATUS      current
     DESCRIPTION
             "This object identifies the Test Id of the session."
     ::= { wwpLeosCfmExtSynLossResponderEntry 1 }
     
  wwpLeosCfmExtSynLossResponderServiceName OBJECT-TYPE
     SYNTAX       DisplayString (SIZE(1..45))
     MAX-ACCESS   read-only
     STATUS       current
     DESCRIPTION
             "This object identifies the CFM service name."
     ::= { wwpLeosCfmExtSynLossResponderEntry 2 }  
      
  wwpLeosCfmExtSynLossResponderLocalMepId OBJECT-TYPE
     SYNTAX      Unsigned32
     MAX-ACCESS  read-only
     STATUS      current
     DESCRIPTION
             "This object identifies the local mepid."
     ::= { wwpLeosCfmExtSynLossResponderEntry 3 } 
     
  wwpLeosCfmExtSynLossResponderLocalMac OBJECT-TYPE
     SYNTAX      MacAddress
     MAX-ACCESS  read-only
     STATUS      current
     DESCRIPTION
             "This object identifies the MAC address of the local mep. "
     ::= { wwpLeosCfmExtSynLossResponderEntry 4 }  
     
  wwpLeosCfmExtSynLossResponderRemoteMepid OBJECT-TYPE
     SYNTAX      	Unsigned32 
     MAX-ACCESS  	read-only
     STATUS      	current
     DESCRIPTION    
             "This object identifies the remote mepid."
     ::= { wwpLeosCfmExtSynLossResponderEntry 5 }   
    
  wwpLeosCfmExtSynLossResponderRemoteMac OBJECT-TYPE
     SYNTAX      MacAddress
     MAX-ACCESS  read-only
     STATUS      current
     DESCRIPTION
             "This object identifies the MAC address of the remote mep."
     ::= { wwpLeosCfmExtSynLossResponderEntry 6 } 
     
  wwpLeosCfmExtSynLossResponderAccelerated OBJECT-TYPE
     SYNTAX      TruthValue
     MAX-ACCESS  read-only
     STATUS      current
     DESCRIPTION
             "This object identifies if the responder is hardware accelerated or not.
              true if Hardware accelerated, false if not."
     ::= { wwpLeosCfmExtSynLossResponderEntry 7 }
     
  wwpLeosCfmExtSynLossResponderNumSLMReceived OBJECT-TYPE
     SYNTAX      Unsigned32
     MAX-ACCESS  read-only
     STATUS      current
     DESCRIPTION
             "This object specifies the number of SLM received by this responder." 
     ::= { wwpLeosCfmExtSynLossResponderEntry 8 } 
     
  wwpLeosCfmExtSynLossResponderNumSLRSent OBJECT-TYPE
     SYNTAX      Unsigned32
     MAX-ACCESS  read-only
     STATUS      current
     DESCRIPTION
             "This object specifies the number of SLR sent by this responder." 
     ::= { wwpLeosCfmExtSynLossResponderEntry 9 }
 --
 -- TCE CFM 
 --
 wwpLeosTceCfmMIBObj       OBJECT IDENTIFIER ::= { wwpLeosCfmMIBObjects 20 } 
 wwpLeosTceCfmMIP          OBJECT IDENTIFIER ::= { wwpLeosTceCfmMIBObj 1 }        
 wwpLeosTceCfmLoopback     OBJECT IDENTIFIER ::= { wwpLeosTceCfmMIBObj 3 }
 wwpLeosTceCfmStack        OBJECT IDENTIFIER ::= { wwpLeosTceCfmMIBObj 5 } 
 wwpLeosTceCfmMEP          OBJECT IDENTIFIER ::=  { wwpLeosTceCfmMIBObj 7}
 wwpLeosTceCfmDelay		   OBJECT IDENTIFIER ::=  { wwpLeosTceCfmMIBObj 12}
 wwpLeosTceCfmFrameLoss    OBJECT IDENTIFIER ::=  { wwpLeosTceCfmMIBObj 13}
 wwpLeosTceCfmMipCCMDb     OBJECT IDENTIFIER ::= { wwpLeosTceCfmMIBObj 14 } 
  
 --
 -- TCE CFM MIP Table
 --
 wwpLeosTceCfmMipTable OBJECT-TYPE
     SYNTAX     SEQUENCE OF WwpLeosTceCfmMipEntry
     MAX-ACCESS not-accessible
     STATUS     current
     DESCRIPTION
            "The (conceptual) table listing the config
            parameters for the CFM MIP Table. This table is not applicable
            if wwpLeosTceCfmServiceType is set to pbtTunnel.
            Any Get/Set/Walk returns an error.
            Not applicable to 39xx/51xx platforms."  
     ::= { wwpLeosTceCfmMIP 1 }
                
 wwpLeosTceCfmMipEntry OBJECT-TYPE
     SYNTAX      WwpLeosTceCfmMipEntry
     MAX-ACCESS  not-accessible
     STATUS      current
     DESCRIPTION
           "An entry (conceptual row) in the wwpLeosTceCfmMipTable."
    INDEX {wwpLeosTceCfmMipLiType, wwpLeosTceCfmMipLiIndex}
     ::= { wwpLeosTceCfmMipTable 1 }
                
 WwpLeosTceCfmMipEntry ::=  SEQUENCE { 
     wwpLeosTceCfmMipLiType              INTEGER,
     wwpLeosTceCfmMipLiIndex             INTEGER,
     wwpLeosTceCfmMipPgid                Unsigned32,
     wwpLeosTceCfmMipBayIndex            Unsigned32,
     wwpLeosTceCfmMipShelfIndex          Unsigned32,
     wwpLeosTceCfmMipModuleIndex         Unsigned32,
     wwpLeosTceCfmMipMacAddr             MacAddress,
     wwpLeosTceCfmMipLevel               INTEGER,
     wwpLeosTceCfmMipStatus              RowStatus,
     wwpLeosTceCfmMipLiName				 DisplayString
 }

 wwpLeosTceCfmMipLiType OBJECT-TYPE
     SYNTAX          INTEGER {
                      subPort(1),
 	 				  pbtService(2), 
	 				  mplsStaticPeMeshVC(3),
					  mplsDynamicPeMeshVC(4),
					  mplsStaticPeSpokeVC(5), 
					  mplsDynamicPeSpokeVC(6),
					  mplsStaticMtuSpokeVC(7),
					  mplsDynamicMtuSpokeVC(8),
					  none(99)
                     }
      MAX-ACCESS    not-accessible
      STATUS        current
      DESCRIPTION
	      "This object specifies an unique index into the table."
      ::= { wwpLeosTceCfmMipEntry 1 }

 wwpLeosTceCfmMipLiIndex OBJECT-TYPE
      SYNTAX        INTEGER (1..65535)
      MAX-ACCESS    not-accessible
      STATUS        current
      DESCRIPTION
	      "This object specifies an unique index into the table."
      ::= { wwpLeosTceCfmMipEntry 2 }
                                                            
 wwpLeosTceCfmMipPgid OBJECT-TYPE
     SYNTAX      Unsigned32
     MAX-ACCESS  read-only
     STATUS      current
     DESCRIPTION
             "This object specifies the port group id."
     ::= { wwpLeosTceCfmMipEntry 3 }
  
 wwpLeosTceCfmMipBayIndex          OBJECT-TYPE
     SYNTAX          Unsigned32 (1..1)
     MAX-ACCESS      read-only
     STATUS          current
     DESCRIPTION
           "This object specifies the chassis bay."               
     ::= { wwpLeosTceCfmMipEntry 4 }
     
 wwpLeosTceCfmMipShelfIndex          OBJECT-TYPE
     SYNTAX          Unsigned32 (1..1)
     MAX-ACCESS      read-only
     STATUS          current
     DESCRIPTION
           "This object specifies the chassis shelf."               
     ::= { wwpLeosTceCfmMipEntry 5 }                  

 wwpLeosTceCfmMipModuleIndex OBJECT-TYPE
     SYNTAX      Unsigned32 (1..7 | 255)
     MAX-ACCESS  read-only
     STATUS      current
     DESCRIPTION
             "This object specifies the chassis module."
     ::= { wwpLeosTceCfmMipEntry 6 }
                    
 wwpLeosTceCfmMipMacAddr OBJECT-TYPE
     SYNTAX      MacAddress
     MAX-ACCESS  read-only
     STATUS      current
     DESCRIPTION
             "This object specifies the MAC address."
     ::= { wwpLeosTceCfmMipEntry 7 }
                    
 wwpLeosTceCfmMipLevel OBJECT-TYPE
     SYNTAX       INTEGER (0..7)
     MAX-ACCESS   read-create
     STATUS       current
     DESCRIPTION
             "This object specifies the level attribute."
     ::= { wwpLeosTceCfmMipEntry 8 }

 wwpLeosTceCfmMipStatus OBJECT-TYPE
     SYNTAX       RowStatus
     MAX-ACCESS   read-create
     STATUS       current
     DESCRIPTION
             "Used to manage the creation and deletion of the conceptual rows in this table.
	     To create a row in this table, set this object to 'createAndGo'.
	     To delete a row in this table, set it to 'destroy'."
     ::= { wwpLeosTceCfmMipEntry 9 } 
 
 wwpLeosTceCfmMipLiName   OBJECT-TYPE
     SYNTAX       DisplayString
     MAX-ACCESS   read-only
     STATUS       current
     DESCRIPTION
             "This object specifies the logical interface name associated with the Mip."
     ::= { wwpLeosTceCfmMipEntry 10 } 
  
  --
  --  CFM Mip CCM Db Table
  --                                   
 wwpLeosTceCfmMipCCMDbTable OBJECT-TYPE
     SYNTAX     SEQUENCE OF WwpLeosTceCfmMipCCMDbEntry
     MAX-ACCESS not-accessible
     STATUS     current
     DESCRIPTION
            "The (conceptual) table listing the display
             parameters for the MIP CCM Db table.
             Not applicable to 6.x"  
     ::= { wwpLeosTceCfmMipCCMDb 1 }
                
 wwpLeosTceCfmMipCCMDbEntry OBJECT-TYPE
     SYNTAX      WwpLeosTceCfmMipCCMDbEntry
     MAX-ACCESS  not-accessible
     STATUS      current
     DESCRIPTION
           "An entry (conceptual row) in the wwpLeosCfmMipCCMDbTable."
     INDEX { wwpLeosTceCfmMipCCMDbIndex }
     ::= { wwpLeosTceCfmMipCCMDbTable 1 }
                
 WwpLeosTceCfmMipCCMDbEntry ::=  SEQUENCE { 
    wwpLeosTceCfmMipCCMDbIndex							 Unsigned32,                     
	wwpLeosTceCfmMipCCMDbMacAddr                         MacAddress,
	wwpLeosTceCfmMipCCMDbServiceName					 DisplayString,
	wwpLeosTceCfmMipCCMDbSubPortName                     DisplayString,
	wwpLeosTceCfmMipCCMdbNumCCMRx                        Counter32,
	wwpLeosTceCfmMipCCMDbCCMRxTime                       Unsigned32,
	wwpLeosTceCfmMipCCMDbLevel							 INTEGER,
	wwpLeosTceCfmMipCCMDbMEPID							 INTEGER,
	wwpLeosTceCfmMipRDI									 INTEGER,
	wwpLeosTceCfmMipLastPortStatus						 INTEGER  	
  }
  
  wwpLeosTceCfmMipCCMDbIndex   OBJECT-TYPE
  	SYNTAX Unsigned32 
  	MAX-ACCESS not-accessible
  	STATUS current
  	DESCRIPTION "This object specifies the Mip CCM database index."
  	::= {   wwpLeosTceCfmMipCCMDbEntry 1 } 
  	
  wwpLeosTceCfmMipCCMDbMacAddr OBJECT-TYPE
  	SYNTAX MacAddress
  	MAX-ACCESS read-only
  	STATUS current
  	DESCRIPTION "This object specifies the MAC address."
  	::= {   wwpLeosTceCfmMipCCMDbEntry 2 } 
  
  wwpLeosTceCfmMipCCMDbServiceName  OBJECT-TYPE
  	SYNTAX DisplayString
  	MAX-ACCESS read-only
  	STATUS current
  	DESCRIPTION "This object specifies the Service Name."
  	::= {   wwpLeosTceCfmMipCCMDbEntry 3 } 
  
   wwpLeosTceCfmMipCCMDbSubPortName OBJECT-TYPE
   	 SYNTAX DisplayString
   	 MAX-ACCESS read-only
   	 STATUS current
   	 DESCRIPTION "This object specifies the SubPort Name."
   	 ::= { wwpLeosTceCfmMipCCMDbEntry 4 }
   
   wwpLeosTceCfmMipCCMdbNumCCMRx OBJECT-TYPE
   	SYNTAX Counter32
   	MAX-ACCESS read-only
   	STATUS current 
   	DESCRIPTION "This object specifies the total Received CCMs."
   	::= {  wwpLeosTceCfmMipCCMDbEntry 5 }
   
   wwpLeosTceCfmMipCCMDbCCMRxTime OBJECT-TYPE
   	 SYNTAX Unsigned32
   	 MAX-ACCESS read-only
   	 STATUS current
   	 DESCRIPTION "This object specifies the CCM Rx Time in milliseconds."
   ::= {  wwpLeosTceCfmMipCCMDbEntry 6 }
  
   wwpLeosTceCfmMipCCMDbLevel OBJECT-TYPE
   	SYNTAX INTEGER  (0..7)
   	MAX-ACCESS read-only
   	STATUS current
   	DESCRIPTION "This object specifies the CCM Db level."                      
   	::= {  wwpLeosTceCfmMipCCMDbEntry 7}
   
   
   wwpLeosTceCfmMipCCMDbMEPID OBJECT-TYPE
   	SYNTAX INTEGER  (1..8191)
   	MAX-ACCESS read-only
   	STATUS current
   	DESCRIPTION "This object specifies the Mep Id."                      
   	::= {  wwpLeosTceCfmMipCCMDbEntry 8}
   
   wwpLeosTceCfmMipRDI OBJECT-TYPE
   	 SYNTAX INTEGER {
   	 			on(1),
   	 			off(2)
   	 		}
   	 MAX-ACCESS read-only
   	 STATUS current
   	 DESCRIPTION "This object specifies the RDI."
   ::= { wwpLeosTceCfmMipCCMDbEntry  9 }
  
  wwpLeosTceCfmMipLastPortStatus OBJECT-TYPE
  	SYNTAX  INTEGER {
  			  blocked(1),
  			  up(2),
  			  none(99)
  			 }
    MAX-ACCESS read-only
    STATUS current
    DESCRIPTION "This object specifies the last port status."
  ::= {wwpLeosTceCfmMipCCMDbEntry 10 }
   
  
  --
  -- TCE Loopback Msg table
  -- 
  wwpLeosTceCfmLoopbackMsgTable OBJECT-TYPE
     SYNTAX     SEQUENCE OF WwpLeosTceCfmLoopbackMsgEntry
     MAX-ACCESS not-accessible
     STATUS     current
     DESCRIPTION
            "The (conceptual) table listing the config parameters for the LoopbackMsg.
             The following attributes are required to create a LoopbackMsg:
             -wwpLeosCfmServiceIndex
             -wwpLeosTceCfmLoopbackMsgSubPortIndex
             -wwpLeosTceCfmLoopbackMsgTargetMEPID or
             -wwpLeosTceCfmLoopbackMsgTargetMacAddr
             -wwpLeosTceCfmLoopbackMsgCount
             -wwpLeosTceCfmLoopbackMsgData
             -wwpLeosTceCfmLoopbackMsgPriority
             -wwpLeosTceCfmLoopbackMsgRowStatus
            Not applicable to 39xx/51xx platforms."  
     ::= { wwpLeosTceCfmLoopback 1 }
                
 wwpLeosTceCfmLoopbackMsgEntry OBJECT-TYPE
     SYNTAX      WwpLeosTceCfmLoopbackMsgEntry
     MAX-ACCESS  not-accessible
     STATUS      current
     DESCRIPTION
           "An entry (conceptual row) in the wwpLeosTceCfmLoopbackMsgTable."
     INDEX {wwpLeosCfmServiceIndex, wwpLeosTceCfmLoopbackMsgLocalMEPID}
     ::= { wwpLeosTceCfmLoopbackMsgTable 1 }
                
 WwpLeosTceCfmLoopbackMsgEntry ::=  SEQUENCE { 
     wwpLeosTceCfmLoopbackMsgLocalMEPID              Unsigned32,
     wwpLeosTceCfmLoopbackMsgTargetMEPID             Unsigned32,
     wwpLeosTceCfmLoopbackMsgTargetMacAddr           MacAddress,
     wwpLeosTceCfmLoopbackMsgCount                   INTEGER,
     wwpLeosTceCfmLoopbackMsgData                    DisplayString,
     wwpLeosTceCfmLoopbackMsgPriority                INTEGER,
     wwpLeosTceCfmLoopbackMsgServiceName             DisplayString,
     wwpLeosTceCfmLoopbackMsgSubPortName             DisplayString,
     wwpLeosTceCfmLoopbackMsgNextLbmTransId          Unsigned32,
     wwpLeosTceCfmLoopbackMsgTotalTxLbm              Unsigned32,
     wwpLeosTceCfmLoopbackMsgTotalRxLbrIo            Unsigned32,
     wwpLeosTceCfmLoopbackMsgTotalRxLbrOoo           Unsigned32,
     wwpLeosTceCfmLoopbackMsgRowStatus               RowStatus,
     wwpLeosTceCfmLoopbackMsgTotalRxLbrContentMismatch Unsigned32,
     wwpLeosTceCfmLoopbackMsgTotalRxLbrUnexpected      Unsigned32
 }

 wwpLeosTceCfmLoopbackMsgLocalMEPID OBJECT-TYPE
     SYNTAX       Unsigned32 (1..8191)
     MAX-ACCESS   not-accessible
     STATUS       current
     DESCRIPTION
             "This object specifies the port."
     ::= { wwpLeosTceCfmLoopbackMsgEntry 1 }
 
 wwpLeosTceCfmLoopbackMsgTargetMEPID OBJECT-TYPE
     SYNTAX       Unsigned32 (1..8191)
     MAX-ACCESS   read-create
     STATUS       current
     DESCRIPTION
             "This object specifies the MEPID.
              This object should only be set if wwpLeosTceCfmLoopbackMsgTargetMacAddr
              is not specified else an error is returned."
     ::= { wwpLeosTceCfmLoopbackMsgEntry 2 }
     
 wwpLeosTceCfmLoopbackMsgTargetMacAddr OBJECT-TYPE
     SYNTAX       MacAddress
     MAX-ACCESS   read-create
     STATUS       current
     DESCRIPTION
             "This object specifies the MacAddress to be used when sending
              link LoopbackMsg. This object should only be set if
              wwpLeosTceCfmLoopbackMsgTargetMEPID is not specified else an error is
              returned."
     ::= { wwpLeosTceCfmLoopbackMsgEntry 3 }
     
 wwpLeosTceCfmLoopbackMsgCount OBJECT-TYPE
     SYNTAX       INTEGER (1..20) 
     MAX-ACCESS   read-create
     STATUS       current
     DESCRIPTION
             "This object specifies the LoopbackMsg count to be used when
              sending link LoopbackMsg. "
     ::= { wwpLeosTceCfmLoopbackMsgEntry 4 }
 
 wwpLeosTceCfmLoopbackMsgData OBJECT-TYPE
     SYNTAX       DisplayString  (SIZE(1..127))
     MAX-ACCESS   read-create
     STATUS       current
     DESCRIPTION                    
             "This object specifies the LoopbackMsg data to be used when
              sending link LoopbackMsg. "
     ::= { wwpLeosTceCfmLoopbackMsgEntry 5 }

 wwpLeosTceCfmLoopbackMsgPriority OBJECT-TYPE
     SYNTAX       INTEGER (0..7)
     MAX-ACCESS   read-create
     STATUS       current
     DESCRIPTION
             "This object specifies the LoopbackMsg priority to be used when
              sending link LoopbackMsg. "
     ::= { wwpLeosTceCfmLoopbackMsgEntry 6 }

 wwpLeosTceCfmLoopbackMsgServiceName OBJECT-TYPE
     SYNTAX       DisplayString (SIZE(1..41))
     MAX-ACCESS   read-only
     STATUS       current
     DESCRIPTION
             "This object specifies the Service used when
              sending link LoopbackMsg."
     ::= { wwpLeosTceCfmLoopbackMsgEntry 7 }        

 wwpLeosTceCfmLoopbackMsgSubPortName OBJECT-TYPE
     SYNTAX       DisplayString (SIZE(1..31))
     MAX-ACCESS   read-only
     STATUS       current
     DESCRIPTION
             "This object specifies the sub-port used when
              sending link LoopbackMsg."
     ::= { wwpLeosTceCfmLoopbackMsgEntry 8 }        

 wwpLeosTceCfmLoopbackMsgNextLbmTransId OBJECT-TYPE
     SYNTAX       Unsigned32
     MAX-ACCESS   read-only
     STATUS       current
     DESCRIPTION
             "This object specifies the next LoopbackMsg transaction id."
     ::= { wwpLeosTceCfmLoopbackMsgEntry 9 }
     
 wwpLeosTceCfmLoopbackMsgTotalTxLbm OBJECT-TYPE
     SYNTAX       Unsigned32
     MAX-ACCESS   read-only
     STATUS       current
     DESCRIPTION
             "This object specifies the total LoopbackMsg sent."
     ::= { wwpLeosTceCfmLoopbackMsgEntry 10 }
     
 wwpLeosTceCfmLoopbackMsgTotalRxLbrIo OBJECT-TYPE
     SYNTAX       Unsigned32
     MAX-ACCESS   read-only
     STATUS       current
     DESCRIPTION
             "This object specifies the total in-order LoopbackMsg received."
     ::= { wwpLeosTceCfmLoopbackMsgEntry 11 }
     
 wwpLeosTceCfmLoopbackMsgTotalRxLbrOoo OBJECT-TYPE
     SYNTAX       Unsigned32
     MAX-ACCESS   read-only
     STATUS       current
     DESCRIPTION
             "This object specifies the total out of order LoopbackMsg received."
     ::= { wwpLeosTceCfmLoopbackMsgEntry 12 }
 
 wwpLeosTceCfmLoopbackMsgRowStatus OBJECT-TYPE
     SYNTAX       RowStatus
     MAX-ACCESS   read-create
     STATUS       current
     DESCRIPTION
             "Used to manage the creation and deletion of the conceptual rows in this table.
	     To send a LoopbackMsg, set this object to 'createAndGo'. 
	     There is no concept of delete a LoopbackMsg in this table."
     ::= { wwpLeosTceCfmLoopbackMsgEntry 13 }

 wwpLeosTceCfmLoopbackMsgTotalRxLbrContentMismatch OBJECT-TYPE
     SYNTAX       Unsigned32
     MAX-ACCESS   read-only
     STATUS       current
     DESCRIPTION
             "This object specifies the total content mismatch LoopbackMsg received."
     ::= { wwpLeosTceCfmLoopbackMsgEntry 14 }

 wwpLeosTceCfmLoopbackMsgTotalRxLbrUnexpected OBJECT-TYPE
     SYNTAX       Unsigned32
     MAX-ACCESS   read-only
     STATUS       current
     DESCRIPTION
             "This object specifies the total unexpected LoopbackMsg received."
     ::= { wwpLeosTceCfmLoopbackMsgEntry 15 }

  --
  --  TCE CFM Port Stack Table
  --                                   
 wwpLeosTceCfmPortStackTable OBJECT-TYPE
     SYNTAX     SEQUENCE OF WwpLeosTceCfmPortStackEntry
     MAX-ACCESS not-accessible
     STATUS     current
     DESCRIPTION
            "The (conceptual) table listing the display
             parameters for the CFM port stack table.
             Not applicable to 6.x"  
     ::= { wwpLeosTceCfmStack 1 }
                
 wwpLeosTceCfmPortStackEntry OBJECT-TYPE
     SYNTAX      WwpLeosTceCfmPortStackEntry
     MAX-ACCESS  not-accessible
     STATUS      current
     DESCRIPTION
           "An entry (conceptual row) in the wwpLeosTceCfmPortStackTable."
     INDEX {wwpLeosTceCfmPortStackServiceType, wwpLeosTceCfmPortStackServiceIndex,
            wwpLeosTceCfmPortStackSubPortType, wwpLeosTceCfmPortStackSubPortIndex}
     ::= { wwpLeosTceCfmPortStackTable 1 }
                
 WwpLeosTceCfmPortStackEntry ::=  SEQUENCE {
     wwpLeosTceCfmPortStackServiceType              INTEGER,
     wwpLeosTceCfmPortStackServiceIndex             Unsigned32,
     wwpLeosTceCfmPortStackSubPortType              INTEGER,
     wwpLeosTceCfmPortStackSubPortIndex             Unsigned32,
     wwpLeosTceCfmPortStackSubPortName              DisplayString,
     wwpLeosTceCfmPortStackOperState                INTEGER,
     wwpLeosTceCfmPortStackPgid                     Unsigned32,
     wwpLeosTceCfmPortStackBayIndex                 Unsigned32,
     wwpLeosTceCfmPortStackShelfIndex               Unsigned32,
     wwpLeosTceCfmPortStackModuleIndex              Unsigned32,
     wwpLeosTceCfmPortStackVsPbtName                DisplayString,
     wwpLeosTceCfmPortStackEgressXformTagValue1     Unsigned32,
     wwpLeosTceCfmPortStackEgressXformTagPriority1  Unsigned32,
     wwpLeosTceCfmPortStackEgressXformTagEtype1     Unsigned32,
     wwpLeosTceCfmPortStackEgressXformTagValue2     Unsigned32,
     wwpLeosTceCfmPortStackEgressXformTagPriority2  Unsigned32,
     wwpLeosTceCfmPortStackEgressXformTagEtype2     Unsigned32,
     wwpLeosTceCfmPortStackMepCount                 Unsigned32,
     wwpLeosTceCfmPortStackMipLevel                 Unsigned32
 }

 wwpLeosTceCfmPortStackServiceType OBJECT-TYPE
     SYNTAX      INTEGER {
                    vs(1),
                    pbt(2)
                 }
     MAX-ACCESS  not-accessible
     STATUS      current
     DESCRIPTION
             "This object specifies the CFM sub-port service type."
     ::= { wwpLeosTceCfmPortStackEntry 1 }
 
 wwpLeosTceCfmPortStackServiceIndex OBJECT-TYPE
     SYNTAX      Unsigned32 (1..65535) 
     MAX-ACCESS  not-accessible
     STATUS      current
     DESCRIPTION
             "A unique identifier for CFM domain entry."
     ::= { wwpLeosTceCfmPortStackEntry 2 }


 wwpLeosTceCfmPortStackSubPortType OBJECT-TYPE
     SYNTAX      INTEGER {
                    vs(1),
                    encapPbt(2), -- future release
                    decapPbt(3)  -- future release
                 }
     MAX-ACCESS  not-accessible
     STATUS      current
     DESCRIPTION
             "This object specifies the CFM sub-port type."
     ::= { wwpLeosTceCfmPortStackEntry 3 }

 wwpLeosTceCfmPortStackSubPortIndex OBJECT-TYPE
     SYNTAX      Unsigned32
     MAX-ACCESS  not-accessible
     STATUS      current
     DESCRIPTION
             "This object specifies the CFM sub-port index."
     ::= { wwpLeosTceCfmPortStackEntry 4 }

 wwpLeosTceCfmPortStackSubPortName OBJECT-TYPE
     SYNTAX      DisplayString (SIZE(1..31))
     MAX-ACCESS  read-only
     STATUS      current
     DESCRIPTION
             "This object specifies the CFM sub-port name."
     ::= { wwpLeosTceCfmPortStackEntry 5 }

 wwpLeosTceCfmPortStackOperState OBJECT-TYPE
     SYNTAX      INTEGER {
                    unknown(1),
                    invalid(2),
                    enabled(3),
                    disabled(4),
                    notAuthenticated(5),
                    loopbackTx(6),    
                    loopbackRx(7),
                    unequipped(8)
                 }
     MAX-ACCESS  read-only
     STATUS      current
     DESCRIPTION
             "This object specifies the CFM sub-port operational state."
     ::= { wwpLeosTceCfmPortStackEntry 6 }

 wwpLeosTceCfmPortStackPgid OBJECT-TYPE
     SYNTAX      Unsigned32
     MAX-ACCESS  read-only
     STATUS      current
     DESCRIPTION
             "This object specifies the CFM sub-port group id."
     ::= { wwpLeosTceCfmPortStackEntry 7 }

 wwpLeosTceCfmPortStackBayIndex  OBJECT-TYPE
     SYNTAX          Unsigned32 (1..1)
     MAX-ACCESS      read-only
     STATUS          current
     DESCRIPTION
           "This object specifies the CFM sub-port agent bay."               
     ::= { wwpLeosTceCfmPortStackEntry 8 }
     
 wwpLeosTceCfmPortStackShelfIndex  OBJECT-TYPE
     SYNTAX          Unsigned32 (1..1)
     MAX-ACCESS      read-only
     STATUS          current
     DESCRIPTION
           "This object specifies the CFM sub-port agent shelf."               
     ::= { wwpLeosTceCfmPortStackEntry 9 }

 wwpLeosTceCfmPortStackModuleIndex OBJECT-TYPE
     SYNTAX      Unsigned32 (1..7 | 255)
     MAX-ACCESS  read-only
     STATUS      current
     DESCRIPTION
             "This object specifies the CFM sub-port agent slot.
              Index value of 255 is reserved for Lag ports."
     ::= { wwpLeosTceCfmPortStackEntry 10 }

 wwpLeosTceCfmPortStackVsPbtName OBJECT-TYPE
     SYNTAX      DisplayString (SIZE(1..32))
     MAX-ACCESS  read-only
     STATUS      current
     DESCRIPTION
             "This object specifies the CFM PBT name."
     ::= { wwpLeosTceCfmPortStackEntry 11 }

 wwpLeosTceCfmPortStackEgressXformTagValue1 OBJECT-TYPE
     SYNTAX      Unsigned32
     MAX-ACCESS  read-only
     STATUS      current
     DESCRIPTION
             "This object specifies the egress tag value."
     ::= { wwpLeosTceCfmPortStackEntry 13 }

 wwpLeosTceCfmPortStackEgressXformTagPriority1 OBJECT-TYPE
     SYNTAX      Unsigned32
     MAX-ACCESS  read-only
     STATUS      current
     DESCRIPTION
             "This object specifies the egress tag priority."
     ::= { wwpLeosTceCfmPortStackEntry 14 }

 wwpLeosTceCfmPortStackEgressXformTagEtype1 OBJECT-TYPE
     SYNTAX      Unsigned32
     MAX-ACCESS  read-only
     STATUS      current
     DESCRIPTION
             "This object specifies the egress tag etype."
     ::= { wwpLeosTceCfmPortStackEntry 15 }

 wwpLeosTceCfmPortStackEgressXformTagValue2 OBJECT-TYPE
     SYNTAX      Unsigned32
     MAX-ACCESS  read-only
     STATUS      current
     DESCRIPTION
             "This object specifies the egress tag value."
     ::= { wwpLeosTceCfmPortStackEntry 16 }

 wwpLeosTceCfmPortStackEgressXformTagPriority2 OBJECT-TYPE
     SYNTAX      Unsigned32
     MAX-ACCESS  read-only
     STATUS      current
     DESCRIPTION
             "This object specifies the egress tag priority."
     ::= { wwpLeosTceCfmPortStackEntry 17 }

 wwpLeosTceCfmPortStackEgressXformTagEtype2 OBJECT-TYPE
     SYNTAX      Unsigned32
     MAX-ACCESS  read-only
     STATUS      current
     DESCRIPTION
             "This object specifies the egress tag etype."
     ::= { wwpLeosTceCfmPortStackEntry 18 }

 wwpLeosTceCfmPortStackMepCount OBJECT-TYPE
     SYNTAX      Unsigned32
     MAX-ACCESS  read-only
     STATUS      current
     DESCRIPTION
             "This object specifies the MEP counts in both directions."
     ::= { wwpLeosTceCfmPortStackEntry 19 }

 wwpLeosTceCfmPortStackMipLevel OBJECT-TYPE
     SYNTAX      Unsigned32
     MAX-ACCESS  read-only
     STATUS      current
     DESCRIPTION
             "This object specifies the port stack MIP level."
     ::= { wwpLeosTceCfmPortStackEntry 20 }
     
  --
  --  CFM MEP Table 
  --                                   
 wwpLeosTceCfmMEPTable OBJECT-TYPE
     SYNTAX     SEQUENCE OF WwpLeosTceCfmMEPEntry
     MAX-ACCESS not-accessible
     STATUS     current
     DESCRIPTION
            "The (conceptual) table listing the config
            parameters for the CFM MEP table.
            Not applicable to 39xx/51xx"  
     ::= { wwpLeosTceCfmMEP 1 }
                
 wwpLeosTceCfmMEPEntry OBJECT-TYPE
     SYNTAX      WwpLeosTceCfmMEPEntry
     MAX-ACCESS  not-accessible
     STATUS      current
     DESCRIPTION
           "An entry (conceptual row) in the wwpLeosCfmMEPTable."
     INDEX {wwpLeosCfmServiceIndex, wwpLeosTceCfmMEPId}
     ::= { wwpLeosTceCfmMEPTable 1 }
                
 WwpLeosTceCfmMEPEntry ::=  SEQUENCE { 
 	 wwpLeosTceCfmMEPId											    Unsigned32,
     wwpLeosTceCfmMEPAdminState                                     INTEGER,        
     wwpLeosTceCfmMEPOperState                                      INTEGER,        
     wwpLeosTceCfmMEPDirection                                      INTEGER,
     wwpLeosTceCfmMEPCCMState            							INTEGER,
     wwpLeosTceCfmMEPCCMPriority         							INTEGER,
     wwpLeosTceCfmMEPLTMPriority         							INTEGER,  
     wwpLeosTceCfmMEPMacAddr                                        MacAddress,
     wwpLeosTceCfmMEPNextLbmSeqNumber                               Counter32,
     wwpLeosTceCfmMEPRxValidInOrderLoopbackReply       			    Counter32,
     wwpLeosTceCfmMEPRxValidOutOrderLoopbackReply          		    Counter32,
     wwpLeosTceCfmMEPNextLTMSeqNumber                               Counter32,
     wwpLeosTceCfmMEPNumLoopbackRepliesTxmt                		    Counter32,
     wwpLeosTceCfmMEPNumLTMRecevied                                 Counter32,
     wwpLeosTceCfmMEPNumLTMTxmt                                     Counter32,
     wwpLeosTceCfmMEPNumCCMTxmt                                     Counter32,     
     wwpLeosTceCfmMEPRowStatus                                      RowStatus,
     wwpLeosTceCfmMEPNumDMMSent									    Counter32,
     wwpLeosTceCfmMEPDMMDelay										Counter32,
     wwpLeosTceCfmMEPDMMJitter										Counter32,
     wwpLeosTceCfmMEPNumLMMSent									    Counter32,
     wwpLeosTceCfmMEPLMMFrameLossNear								Counter32,
     wwpLeosTceCfmMEPLMMFrameLossFar								Counter32,
     wwpLeosTceCfmMEPLiType											INTEGER,
     wwpLeosTceCfmMEPLiIndex										Unsigned32,
     wwpLeosTceCfmMEPServiceName                                    DisplayString,
     wwpLeosTceCfmMEPSubPortName                                    DisplayString,
     wwpLeosTceCfmMEPVsPbtName                                      DisplayString,
     wwpLeosTceCfmMEPLogicalPortName                                DisplayString,
     wwpLeosTceCfmMEPSubPortIndex                                   Unsigned32,
     wwpLeosTceCfmMEPEncapsulation                                  INTEGER,
     wwpLeosTceCfmMEPLeadPortBayIndex                               Unsigned32,
     wwpLeosTceCfmMEPLeadPortShelfIndex                             Unsigned32,
     wwpLeosTceCfmMEPLeadPortModuleIndex                            Unsigned32,
     wwpLeosTceCfmMEPPBTBvid                                        Unsigned32,
     wwpLeosTceCfmMEPPBTEtype                                       Unsigned32,
     wwpLeosTceCfmMEPNumLbmTxmt                                     Counter32,
     wwpLeosTceCfmMEPNumLbmReceived                                 Counter32,
     wwpLeosTceCfmMEPNumLoopbackRepliesReceived                     Counter32,
     wwpLeosTceCfmMEPNumLTRepliesTxmt                               Counter32,
     wwpLeosTceCfmMEPNumLTRepliesReceived                           Counter32,
     wwpLeosTceCfmMEPNumUnexpectedLTRepliesReceived                 Counter32,
     wwpLeosTceCfmMEPNumCCMReceived                                 Counter32,
     wwpLeosTceCfmMEPRxContentMismatchLoopbackReply                 Counter32,
     wwpLeosTceCfmMEPRxUnexpectedLoopbackReply                      Counter32
 }
   
 wwpLeosTceCfmMEPId OBJECT-TYPE
     SYNTAX      Unsigned32 (1..8191)
     MAX-ACCESS  not-accessible
     STATUS      current
     DESCRIPTION
             "This is used as the index in the table.
	     This object specifies the mep id for the given service."
     ::= { wwpLeosTceCfmMEPEntry 1 }

 wwpLeosTceCfmMEPAdminState OBJECT-TYPE
     SYNTAX      INTEGER   {
                                disabled(1),
                                enabled(2)  
                          }
     MAX-ACCESS  read-write
     STATUS      current
     DESCRIPTION
             "This object specifies the admin state of CFM MEP."
     ::= { wwpLeosTceCfmMEPEntry 2 }
 
 wwpLeosTceCfmMEPOperState OBJECT-TYPE
     SYNTAX      INTEGER   {
                                disabled(1),
                                enabled(2)  
                          }
     MAX-ACCESS  read-only
     STATUS      current
     DESCRIPTION
             "This object specifies the oper state of CFM MEP."
     ::= { wwpLeosTceCfmMEPEntry 3 }
     
 wwpLeosTceCfmMEPDirection OBJECT-TYPE
     SYNTAX      INTEGER {
                                up(1),
                                down(2)
                         }
     MAX-ACCESS  read-create
     STATUS      current
     DESCRIPTION
             "This object specifies the MEP direction of the service.
              This object can only be set if wwpLeosCfmServiceIndex is of type vlan."
     ::= { wwpLeosTceCfmMEPEntry 4 } 
 
 wwpLeosTceCfmMEPCCMState OBJECT-TYPE
     SYNTAX       INTEGER {
                                on(1),
                                off(2)
                                }
     MAX-ACCESS   read-write
     STATUS       current
     DESCRIPTION
             "This object specifies the CCM transmission for the service specified by wwpLeosCfmServiceType."
     ::= { wwpLeosTceCfmMEPEntry 5 }
     
 wwpLeosTceCfmMEPCCMPriority OBJECT-TYPE
     SYNTAX       INTEGER (0..7)
     MAX-ACCESS   read-write
     STATUS       current
     DESCRIPTION
             "This object specifies the priority of CCM messages transmitted."
     ::= { wwpLeosTceCfmMEPEntry 6 }
     
 wwpLeosTceCfmMEPLTMPriority OBJECT-TYPE
     SYNTAX      INTEGER (0..7)
     MAX-ACCESS  read-write
     STATUS      current
     DESCRIPTION
             "This object specifies the priority received on the given service and port."
     ::= { wwpLeosTceCfmMEPEntry 7 } 
     
   
 wwpLeosTceCfmMEPMacAddr OBJECT-TYPE
     SYNTAX      MacAddress
     MAX-ACCESS  read-only
     STATUS      current
     DESCRIPTION
             "This object specifies the MAC address received on the given service and port.."
     ::= { wwpLeosTceCfmMEPEntry 8 }
     
 wwpLeosTceCfmMEPNextLbmSeqNumber OBJECT-TYPE
     SYNTAX      Counter32 
     MAX-ACCESS  read-only
     STATUS      current
     DESCRIPTION
             "This object specifies the next LBM sequence number received on the given service and port."
     ::= { wwpLeosTceCfmMEPEntry 9 }
     
 wwpLeosTceCfmMEPRxValidInOrderLoopbackReply OBJECT-TYPE
     SYNTAX      Counter32
     MAX-ACCESS  read-only
     STATUS      current
     DESCRIPTION
             "This object specifies the total valid in order loopback replies received on the given service and port."
     ::= { wwpLeosTceCfmMEPEntry 10 }
     
 wwpLeosTceCfmMEPRxValidOutOrderLoopbackReply OBJECT-TYPE
     SYNTAX      Counter32
     MAX-ACCESS  read-only
     STATUS      current
     DESCRIPTION
             "This object specifies the total valid out of order loopback replies received on the given service and port."
     ::= { wwpLeosTceCfmMEPEntry 11 }
     
 wwpLeosTceCfmMEPNextLTMSeqNumber OBJECT-TYPE
     SYNTAX      Counter32 
     MAX-ACCESS  read-only
     STATUS      current
     DESCRIPTION
             "This object specifies the next LTM sequence number received on the given service and port."
     ::= { wwpLeosTceCfmMEPEntry 12 }
     
 wwpLeosTceCfmMEPNumLoopbackRepliesTxmt OBJECT-TYPE
     SYNTAX      Counter32
     MAX-ACCESS  read-only
     STATUS      current
     DESCRIPTION
             "This object specifies the flags total loopback replies transmitted on the given service and port."
     ::= { wwpLeosTceCfmMEPEntry 13 }
     
 wwpLeosTceCfmMEPNumLTMRecevied OBJECT-TYPE
     SYNTAX      Counter32
     MAX-ACCESS  read-only
     STATUS      current
     DESCRIPTION
             "This object specifies the total LTM messages received on the given service and port."
     ::= { wwpLeosTceCfmMEPEntry 14 }
     
 wwpLeosTceCfmMEPNumLTMTxmt OBJECT-TYPE
     SYNTAX      Counter32
     MAX-ACCESS  read-only
     STATUS      current
     DESCRIPTION
             "This object specifies the total LTM transmitted on the given service and port."
     ::= { wwpLeosTceCfmMEPEntry 15 }
     
 wwpLeosTceCfmMEPNumCCMTxmt OBJECT-TYPE
     SYNTAX      Counter32
     MAX-ACCESS  read-only
     STATUS      current
     DESCRIPTION
             "This object specifies the total CCM messages transmitted on the given service and port."
     ::= { wwpLeosTceCfmMEPEntry 16 }     
     
 wwpLeosTceCfmMEPRowStatus OBJECT-TYPE
     SYNTAX       RowStatus
     MAX-ACCESS   read-create
     STATUS       current
     DESCRIPTION
             "Used to manage the creation and deletion of the conceptual rows in this table.
	     To create a row in this table, set this object to 'createAndGo'.
	     To delete a row in this table, set this to 'destroy'."
     ::= { wwpLeosTceCfmMEPEntry 17 }  
     
  wwpLeosTceCfmMEPNumDMMSent OBJECT-TYPE
     SYNTAX      Counter32
     MAX-ACCESS  read-only
     STATUS      current
     DESCRIPTION
             "This object specifies the total delay measurement messages
             transmitted on the given service and port."
     ::= { wwpLeosTceCfmMEPEntry 18 } 
     
 wwpLeosTceCfmMEPDMMDelay OBJECT-TYPE
     SYNTAX      Counter32
     MAX-ACCESS  read-only
     STATUS      current
     DESCRIPTION
             "This object specifies the average delay in microseconds
             measured during the last DMM performance test on the given service and port."
     ::= { wwpLeosTceCfmMEPEntry 19 } 
     
 wwpLeosTceCfmMEPDMMJitter OBJECT-TYPE
     SYNTAX      Counter32
     MAX-ACCESS  read-only
     STATUS      current
     DESCRIPTION
             "This object specifies the average jitter in microseconds
             measured during the last DMM performance test on the given service and port."
     ::= { wwpLeosTceCfmMEPEntry 20 }
 
 wwpLeosTceCfmMEPNumLMMSent OBJECT-TYPE
     SYNTAX      Counter32
     MAX-ACCESS  read-only
     STATUS      current
     DESCRIPTION
             "This object specifies the total frame loss measurement messages
             transmitted on the given service and port."
     ::= { wwpLeosTceCfmMEPEntry 21 } 
     
 wwpLeosTceCfmMEPLMMFrameLossNear OBJECT-TYPE
     SYNTAX      Counter32
     MAX-ACCESS  read-only
     STATUS      current
     DESCRIPTION
             "This object specifies the number of lost frames on the near side
             measured during the last LMM performance test on the given service and port."
     ::= { wwpLeosTceCfmMEPEntry 22 } 
     
 wwpLeosTceCfmMEPLMMFrameLossFar OBJECT-TYPE
     SYNTAX      Counter32
     MAX-ACCESS  read-only
     STATUS      current
     DESCRIPTION
             "This object specifies the number of lost frames on the far side
             measured during the last LMM performance test on the given service and port."
     ::= { wwpLeosTceCfmMEPEntry 23 }  
  
 wwpLeosTceCfmMEPLiType   OBJECT-TYPE
 	 SYNTAX      INTEGER {
 	 				   vs(1),
 	 				   pbtService(2), 
	 				   mplsStaticPeMeshVC(3),
					   mplsDynamicPeMeshVC(4),
					   mplsStaticPeSpokeVC(5), 
					   mplsDynamicPeSpokeVC(6),
					   mplsStaticMtuSpokeVC(7),
					   mplsDynamicMtuSpokeVC(8),
 	 				   none(99)
 	 		     }
     MAX-ACCESS  read-create
     STATUS      current
     DESCRIPTION
             "This object specifies the LiType on which the Mep is created."
     ::= { wwpLeosTceCfmMEPEntry 24 }  
 
 wwpLeosTceCfmMEPLiIndex OBJECT-TYPE
 	SYNTAX    Unsigned32
 	MAX-ACCESS read-create
 	STATUS current
 	DESCRIPTION
 		"This object specifies the LiIndex for creating the MEP." 
 	::= { wwpLeosTceCfmMEPEntry 25 } 
  
 wwpLeosTceCfmMEPServiceName OBJECT-TYPE
     SYNTAX      DisplayString (SIZE(0..41))
     MAX-ACCESS  read-only
     STATUS      current
     DESCRIPTION
             "This object specifies the service name assigned to this port."
     ::= { wwpLeosTceCfmMEPEntry 50 }
  
 wwpLeosTceCfmMEPSubPortName OBJECT-TYPE
     SYNTAX      DisplayString (SIZE(0..31))
     MAX-ACCESS  read-only
     STATUS      current
     DESCRIPTION
             "This object represents the sub-port, PbtService or Mpls Vc name assigned to the given service and port." 
     ::= { wwpLeosTceCfmMEPEntry 51 }

 wwpLeosTceCfmMEPVsPbtName OBJECT-TYPE
     SYNTAX      DisplayString (SIZE(0..31))
     MAX-ACCESS  read-only
     STATUS      current
     DESCRIPTION
             "This object represents the virtual switch or Pbt tunnel assigned to the given service and port." 
     ::= { wwpLeosTceCfmMEPEntry 52 }

 wwpLeosTceCfmMEPLogicalPortName OBJECT-TYPE
     SYNTAX      DisplayString (SIZE(0..31))
     MAX-ACCESS  read-only
     STATUS      current
     DESCRIPTION
             "This object represents the logical port name assigned to the given service and port." 
     ::= { wwpLeosTceCfmMEPEntry 53 }

 wwpLeosTceCfmMEPSubPortIndex OBJECT-TYPE
     SYNTAX      Unsigned32
     MAX-ACCESS  read-write
     STATUS      current
     DESCRIPTION
             "This object specifies the CFM sub-port index."
     ::= { wwpLeosTceCfmMEPEntry 54 }

 wwpLeosTceCfmMEPEncapsulation OBJECT-TYPE
     SYNTAX      INTEGER {
                                ieee802dot1d(1),
                                pbtCfmEncap(2)
                         }
     MAX-ACCESS  read-only
     STATUS      current
     DESCRIPTION
             "This object specifies the encapsulation applied to the service and port."
     ::= { wwpLeosTceCfmMEPEntry 55 } 
 
 wwpLeosTceCfmMEPLeadPortBayIndex OBJECT-TYPE
     SYNTAX          Unsigned32 (1..1)
     MAX-ACCESS      read-only
     STATUS          current
     DESCRIPTION
           "This object specifies the agent bay the MEP is in."               
     ::= { wwpLeosTceCfmMEPEntry 56 }

 wwpLeosTceCfmMEPLeadPortShelfIndex OBJECT-TYPE
     SYNTAX          Unsigned32 (1..1)
     MAX-ACCESS      read-only
     STATUS          current
     DESCRIPTION
           "This object specifies the agent shelf the MEP is in."               
     ::= { wwpLeosTceCfmMEPEntry 57 }

 wwpLeosTceCfmMEPLeadPortModuleIndex OBJECT-TYPE
     SYNTAX          Unsigned32 (1..7 | 255)
     MAX-ACCESS      read-only
     STATUS          current
     DESCRIPTION
           "This object specifies the agent module the MEP is in.
            Index = 255 is reserved for Lag ports and this object cannot be set to 255
            in this table."               
     ::= { wwpLeosTceCfmMEPEntry 58 }
     
 wwpLeosTceCfmMEPPBTBvid OBJECT-TYPE
     SYNTAX          Unsigned32 (1..8191)
     MAX-ACCESS      read-only
     STATUS          current
     DESCRIPTION
             "This object specifies the BVID assigned to the given service and port."
     ::= { wwpLeosTceCfmMEPEntry 59 }

 wwpLeosTceCfmMEPPBTEtype OBJECT-TYPE
     SYNTAX          Unsigned32 (1..8191)
     MAX-ACCESS      read-only
     STATUS          current
     DESCRIPTION
             "This object specifies the E-type assigned to the given service and port."
     ::= { wwpLeosTceCfmMEPEntry 60 }

 wwpLeosTceCfmMEPNumLbmTxmt OBJECT-TYPE
     SYNTAX      Counter32
     MAX-ACCESS  read-only
     STATUS      current
     DESCRIPTION
             "This object specifies the total loopback messages transmitted on the 
              given service and port."
     ::= { wwpLeosTceCfmMEPEntry 61 }
     
 wwpLeosTceCfmMEPNumLbmReceived OBJECT-TYPE
     SYNTAX      Counter32
     MAX-ACCESS  read-only
     STATUS      current
     DESCRIPTION
             "This object specifies the total loopback messages received on the 
              given service and port."
     ::= { wwpLeosTceCfmMEPEntry 62 }

 wwpLeosTceCfmMEPNumLoopbackRepliesReceived OBJECT-TYPE
     SYNTAX      Counter32
     MAX-ACCESS  read-only
     STATUS      current
     DESCRIPTION
             "This object specifies the total loopback replies received on the 
              given service and port."
     ::= { wwpLeosTceCfmMEPEntry 63 }

 wwpLeosTceCfmMEPNumLTRepliesTxmt OBJECT-TYPE
     SYNTAX      Counter32
     MAX-ACCESS  read-only
     STATUS      current
     DESCRIPTION
             "This object specifies the total link trace replies transmitted on the 
              given service and port."
     ::= { wwpLeosTceCfmMEPEntry 64 }

 wwpLeosTceCfmMEPNumLTRepliesReceived OBJECT-TYPE
     SYNTAX      Counter32
     MAX-ACCESS  read-only
     STATUS      current
     DESCRIPTION
             "This object specifies the total link trace replies received on the 
              given service and port."
     ::= { wwpLeosTceCfmMEPEntry 65 }

 wwpLeosTceCfmMEPNumUnexpectedLTRepliesReceived OBJECT-TYPE
     SYNTAX      Counter32
     MAX-ACCESS  read-only
     STATUS      current
     DESCRIPTION
             "This object specifies the total unexpected link trace replies received on the 
              given service and port."
     ::= { wwpLeosTceCfmMEPEntry 66 }

 wwpLeosTceCfmMEPNumCCMReceived OBJECT-TYPE
     SYNTAX      Counter32
     MAX-ACCESS  read-only
     STATUS      current
     DESCRIPTION
             "This object specifies the total CCM messages received on the given service and port."
     ::= { wwpLeosTceCfmMEPEntry 67 }

 wwpLeosTceCfmMEPRxContentMismatchLoopbackReply OBJECT-TYPE
     SYNTAX      Counter32
     MAX-ACCESS  read-only
     STATUS      current
     DESCRIPTION
             "This object specifies the total content mismatch loopback replies received on the given service and port."
     ::= { wwpLeosTceCfmMEPEntry 68 }

 wwpLeosTceCfmMEPRxUnexpectedLoopbackReply OBJECT-TYPE
     SYNTAX      Counter32
     MAX-ACCESS  read-only
     STATUS      current
     DESCRIPTION
             "This object specifies the total unexpected loopback replies received on the given service and port."
     ::= { wwpLeosTceCfmMEPEntry 69 }

 --
  -- Delay Measurement Msg table
  -- 
  wwpLeosTceCfmDelayMsgTable OBJECT-TYPE
     SYNTAX     SEQUENCE OF WwpLeosTceCfmDelayMsgEntry
     MAX-ACCESS not-accessible
     STATUS     current
     DESCRIPTION
            "The (conceptual) table listing the config
            parameters for the DelayMeasurementMsg.
            Not applicable to 6.x"
            
     ::= { wwpLeosTceCfmDelay 1 }
                
 wwpLeosTceCfmDelayMsgEntry OBJECT-TYPE
     SYNTAX      WwpLeosTceCfmDelayMsgEntry
     MAX-ACCESS  not-accessible
     STATUS      current
     DESCRIPTION
           "An entry (conceptual row) in the wwpLeosCfmDelayMsgTable.
           To send, clear or cancel the message, the corresponding MsgAction 
           needs to be specified. Individual objects in this table
           cannot be set.                                     
           RowStatus is a read-only field.
           To send or cancel a message, the TargetMepID or the 
           TargtetMacAddr objects need to be specified.
           Clear msgAction clears the counters for the message"
     INDEX {wwpLeosCfmServiceIndex, wwpLeosTceCfmDelayMsgLocalMEPId}
     ::= { wwpLeosTceCfmDelayMsgTable 1 }
                
 WwpLeosTceCfmDelayMsgEntry ::=  SEQUENCE { 
     wwpLeosTceCfmDelayMsgLocalMEPId                  	INTEGER,
     wwpLeosTceCfmDelayMsgTargetMEPID              Unsigned32,
     wwpLeosTceCfmDelayMsgTargetMacAddr            MacAddress,
     wwpLeosTceCfmDelayMsgCount                   	INTEGER,
     wwpLeosTceCfmDelayMsgPriority                	INTEGER,
     wwpLeosTceCfmDelayMsgRowStatus               	RowStatus,
     wwpLeosTceCfmDelayMsgRepeatInterval			Unsigned32,
     wwpLeosTceCfmDelayMsgDelayThreshold			INTEGER,
     wwpLeosTceCfmDelayMsgJitterThreshold			INTEGER,
     wwpLeosTceCfmDelayMsgServiceName				DisplayString,
     wwpLeosTceCfmDelayMsgSubPortName				DisplayString,
     wwpLeosTceCfmDelayMsgDelay					    Unsigned32,
     wwpLeosTceCfmDelayMsgJitter					Unsigned32,
     wwpLeosTceCfmDelayMsgTotalTxDmm				Unsigned32,
     wwpLeosTceCfmDelayMsgTotalRxDmm				Unsigned32,
     wwpLeosTceCfmDelayMsgTotalTxDmr				Unsigned32,
     wwpLeosTceCfmDelayMsgTotalRxDmr				Unsigned32,  
     wwpLeosTceCfmDelayMsgAction					SendState,
     wwpLeosTceCfmDelayMsgMaxDelay			        Unsigned32,
     wwpLeosTceCfmDelayMsgMaxJitter					Unsigned32, 
     wwpLeosTceCfmDelayMsgMaxDelayThreshold         INTEGER,
     wwpLeosTceCfmDelayMsgMaxJitterThreshold        INTEGER,
     wwpLeosTceCfmDelayMsgMinDelay			        Unsigned32,
     wwpLeosTceCfmDelayMsgMinJitter					Unsigned32
     
 }

 wwpLeosTceCfmDelayMsgLocalMEPId OBJECT-TYPE
     SYNTAX       INTEGER (1..65535)
     MAX-ACCESS   read-only
     STATUS       current
     DESCRIPTION
             "This object specifies the local MEPId."
     ::= { wwpLeosTceCfmDelayMsgEntry 1 }
 
 wwpLeosTceCfmDelayMsgTargetMEPID OBJECT-TYPE
     SYNTAX       Unsigned32 (1..8191)
     MAX-ACCESS   read-create
     STATUS       current
     DESCRIPTION
             "This object specifies the MEPID.
              This object should only be set if wwpLeosTceCfmDelayMsgTargetMacAddr is not specified else
              an error is returned."
     ::= { wwpLeosTceCfmDelayMsgEntry 2 }
     
 wwpLeosTceCfmDelayMsgTargetMacAddr OBJECT-TYPE
     SYNTAX       MacAddress
     MAX-ACCESS   read-create
     STATUS       current
     DESCRIPTION
             "This object specifies the MAC address to be used when sending link LoopbackMsg.
              This object should only be set if wwpLeosTceCfmDelayMsgTargetMEPID is not specified else
              an error is returned."
     ::= {wwpLeosTceCfmDelayMsgEntry 3 }
     
 wwpLeosTceCfmDelayMsgCount OBJECT-TYPE
     SYNTAX       INTEGER (2..9000) 
     MAX-ACCESS   read-create
     STATUS       current
     DESCRIPTION
             "This object specifies the DelayMeasurementMsg count to be used
              when sending link DelayMeasurementMsg."
     ::= { wwpLeosTceCfmDelayMsgEntry 4 }
 
 wwpLeosTceCfmDelayMsgPriority OBJECT-TYPE
     SYNTAX       INTEGER (0..7)
     MAX-ACCESS   read-create
     STATUS       current
     DESCRIPTION
             "This object specifies the DelayMeasurementMsg priority to be
             used when sending link DelayMeasurementMsg."
     ::= { wwpLeosTceCfmDelayMsgEntry 5 }
 
 wwpLeosTceCfmDelayMsgRowStatus OBJECT-TYPE
     SYNTAX       RowStatus
     MAX-ACCESS   read-only
     STATUS       current
     DESCRIPTION
             "This object is a display read-only field only. A row in this table
             is created by the system when a service and mep are created."
     ::= { wwpLeosTceCfmDelayMsgEntry 6 }
 
  wwpLeosTceCfmDelayMsgRepeatInterval OBJECT-TYPE
     SYNTAX       Unsigned32 (0..1440)
     UNITS		  "minutes"
     MAX-ACCESS   read-create
     STATUS       current
     DESCRIPTION
             "This object represents the transmission period for the CFM delay."
     ::= { wwpLeosTceCfmDelayMsgEntry 40 }

   wwpLeosTceCfmDelayMsgDelayThreshold OBJECT-TYPE
     SYNTAX       INTEGER (1..65535)
     MAX-ACCESS   read-create
     STATUS       current
     DESCRIPTION
             "This object represents the Threshold for the average delay."
     ::= {wwpLeosTceCfmDelayMsgEntry 41 }
  
  wwpLeosTceCfmDelayMsgJitterThreshold OBJECT-TYPE
     SYNTAX       INTEGER  (1..65535)
     MAX-ACCESS   read-create
     STATUS       current
     DESCRIPTION
             "This object represents the threshold value for the jitter."
     ::= { wwpLeosTceCfmDelayMsgEntry 42 }   
    
  wwpLeosTceCfmDelayMsgServiceName OBJECT-TYPE
     SYNTAX       DisplayString (SIZE(1..41))
     MAX-ACCESS   read-only
     STATUS       current
     DESCRIPTION
             "This object specifies the service to be used when
 	sending DelayMsg."
     ::= { wwpLeosTceCfmDelayMsgEntry 43 }
 
  wwpLeosTceCfmDelayMsgSubPortName OBJECT-TYPE
     SYNTAX       DisplayString (SIZE(1..31))
     MAX-ACCESS   read-only
     STATUS       current
     DESCRIPTION
             "This object represents the sub-port name where the DelayMsg
 	was sent."
     ::= { wwpLeosTceCfmDelayMsgEntry 44 }
   
  wwpLeosTceCfmDelayMsgDelay OBJECT-TYPE
     SYNTAX       Unsigned32
     UNITS		  "microseconds"
     MAX-ACCESS   read-only
     STATUS       current
     DESCRIPTION
             "This object specifies the average delay."
     ::= { wwpLeosTceCfmDelayMsgEntry 50 }
  
  wwpLeosTceCfmDelayMsgJitter OBJECT-TYPE
     SYNTAX       Unsigned32
     UNITS		  "microseconds"
     MAX-ACCESS   read-only
     STATUS       current
     DESCRIPTION
             "This object specifies the average jitter."
     ::= { wwpLeosTceCfmDelayMsgEntry 51 }   
        
   wwpLeosTceCfmDelayMsgTotalTxDmm OBJECT-TYPE
     SYNTAX       Unsigned32
     MAX-ACCESS   read-only
     STATUS       current
     DESCRIPTION
             "This object specifies the total Delaymessages transmitted."
     ::= { wwpLeosTceCfmDelayMsgEntry 52 }
  
  wwpLeosTceCfmDelayMsgTotalRxDmm OBJECT-TYPE
     SYNTAX       Unsigned32
     MAX-ACCESS   read-only
     STATUS       current
     DESCRIPTION
             "This object specifies the total Delaymessages received."
     ::= { wwpLeosTceCfmDelayMsgEntry 53 }
 
 wwpLeosTceCfmDelayMsgTotalTxDmr OBJECT-TYPE
     SYNTAX       Unsigned32
     MAX-ACCESS   read-only
     STATUS       current
     DESCRIPTION
             "This object represents the total DMRs transmitted."
     ::= { wwpLeosTceCfmDelayMsgEntry 54 }
     
  wwpLeosTceCfmDelayMsgTotalRxDmr OBJECT-TYPE
     SYNTAX       Unsigned32
     MAX-ACCESS   read-only
     STATUS       current
     DESCRIPTION
             "This object represents the total DMRs received."
     ::= { wwpLeosTceCfmDelayMsgEntry 55 }    
  
  wwpLeosTceCfmDelayMsgAction OBJECT-TYPE
     SYNTAX       SendState
     MAX-ACCESS   read-create
     STATUS       current
     DESCRIPTION
             "This object represents the action for the message (send, clear or cancel)"
     ::= { wwpLeosTceCfmDelayMsgEntry 56 } 
     
   wwpLeosTceCfmDelayMsgMaxDelay OBJECT-TYPE
     SYNTAX       Unsigned32
     UNITS		  "microseconds"
     MAX-ACCESS   read-only
     STATUS       current
     DESCRIPTION
             "This object represents the maximum delay."
     ::= { wwpLeosTceCfmDelayMsgEntry 57 }
  
  wwpLeosTceCfmDelayMsgMaxJitter OBJECT-TYPE
     SYNTAX       Unsigned32
     UNITS		  "microseconds"
     MAX-ACCESS   read-only
     STATUS       current
     DESCRIPTION
             "This object represents the maximum jitter"
     ::= { wwpLeosTceCfmDelayMsgEntry 58 }  

  wwpLeosTceCfmDelayMsgMaxDelayThreshold OBJECT-TYPE
     SYNTAX       INTEGER (1..65535)
     MAX-ACCESS   read-create
     STATUS       current
     DESCRIPTION
             "This object represents the threshold for maximum delay"
     ::= {wwpLeosTceCfmDelayMsgEntry 59 }
  
  wwpLeosTceCfmDelayMsgMaxJitterThreshold OBJECT-TYPE
     SYNTAX       INTEGER  (1..65535)
     MAX-ACCESS   read-create
     STATUS       current
     DESCRIPTION
             "This object represents the threshold value for maximum jitter."
     ::= { wwpLeosTceCfmDelayMsgEntry 60 }
     
  wwpLeosTceCfmDelayMsgMinDelay OBJECT-TYPE
     SYNTAX       Unsigned32
     UNITS		  "microseconds"
     MAX-ACCESS   read-only
     STATUS       current
     DESCRIPTION
             "This object represents the maximum delay"
     ::= { wwpLeosTceCfmDelayMsgEntry 61 }
  
  wwpLeosTceCfmDelayMsgMinJitter OBJECT-TYPE
     SYNTAX       Unsigned32
     UNITS		  "microseconds"
     MAX-ACCESS   read-only
     STATUS       current
     DESCRIPTION
             "This object represents the maximum jitter"
     ::= { wwpLeosTceCfmDelayMsgEntry 62 }      
     
  
  --
  -- Frame Loss Measurement Msg table
  -- 
  wwpLeosTceCfmFrameLossMsgTable OBJECT-TYPE
     SYNTAX     SEQUENCE OF WwpLeosTceCfmFrameLossMsgEntry
     MAX-ACCESS not-accessible
     STATUS     current
     DESCRIPTION
            "The (conceptual) table listing the config
            parameters for the FrameLossMeasurementMsg.
            Not applicable to 6.x"  
     ::= { wwpLeosTceCfmFrameLoss 1 }
                
 wwpLeosTceCfmFrameLossMsgEntry OBJECT-TYPE
     SYNTAX      WwpLeosTceCfmFrameLossMsgEntry
     MAX-ACCESS  not-accessible
     STATUS      current
     DESCRIPTION
           "An entry (conceptual row) in the wwpLeosCfmFrameLossMsgTable.
           To send, clear or cancel the message, the corresponding MsgAction
           needs to be specified. Individual objects in this table
           cannot be set.                                     
           RowStatus is a read-only field.
           To send or cancel a message, the TargetMepID or the 
           TargtetMacAddr objects need to be specified.
           Clear msgAction clears the counters for the message"

     INDEX {wwpLeosCfmServiceIndex, wwpLeosTceCfmFrameLossMsgLocalMEPId}
     ::= { wwpLeosTceCfmFrameLossMsgTable 1 }
                
 WwpLeosTceCfmFrameLossMsgEntry ::=  SEQUENCE { 
     wwpLeosTceCfmFrameLossMsgLocalMEPId                  	INTEGER,
     wwpLeosTceCfmFrameLossMsgTargetMEPID              Unsigned32,
     wwpLeosTceCfmFrameLossMsgTargetMacAddr            MacAddress,
     wwpLeosTceCfmFrameLossMsgCount                   	INTEGER,
     wwpLeosTceCfmFrameLossMsgPriority                	INTEGER,
     wwpLeosTceCfmFrameLossMsgRowStatus               	RowStatus,
     wwpLeosTceCfmFrameLossMsgRepeatInterval			Unsigned32,
     wwpLeosTceCfmFrameLossMsgNearLossThreshold     	INTEGER,
     wwpLeosTceCfmFrameLossMsgFarLossThreshold			INTEGER,
     wwpLeosTceCfmFrameLossMsgServiceName				DisplayString,
     wwpLeosTceCfmFrameLossMsgSubPortName				DisplayString,
     wwpLeosTceCfmFrameLossMsgFrameLossNear			Unsigned32,
     wwpLeosTceCfmFrameLossMsgFrameLossFar				Unsigned32,
     wwpLeosTceCfmFrameLossMsgTotalTxLmm				Unsigned32,
     wwpLeosTceCfmFrameLossMsgTotalRxLmm				Unsigned32,
     wwpLeosTceCfmFrameLossMsgTotalTxLmr				Unsigned32,
     wwpLeosTceCfmFrameLossMsgTotalRxLmr				Unsigned32,
     wwpLeosTceCfmFrameLossMsgAction					SendState     
 }
  wwpLeosTceCfmFrameLossMsgLocalMEPId OBJECT-TYPE
     SYNTAX       INTEGER (1..65535)
     MAX-ACCESS   accessible-for-notify
     STATUS       current
     DESCRIPTION
             "This object specifies the Local MEPID at the source."
     ::= { wwpLeosTceCfmFrameLossMsgEntry 1 }
 
 wwpLeosTceCfmFrameLossMsgTargetMEPID OBJECT-TYPE
     SYNTAX       Unsigned32 (1..8191)
     MAX-ACCESS   read-create
     STATUS       current
     DESCRIPTION
             "This object specifies the MEPID.
              This object should only be set if wwpLeosTceCfmFrameLossMsgTargetMacAddr is not specified else
              an error is returned."
     ::= { wwpLeosTceCfmFrameLossMsgEntry 2 }
     
 wwpLeosTceCfmFrameLossMsgTargetMacAddr OBJECT-TYPE
     SYNTAX       MacAddress
     MAX-ACCESS   read-create
     STATUS       current
     DESCRIPTION
             "This object specifies the MacAddress to be used when sending link LoopbackMsg.
              This object should only be set if wwpLeosTceCfmFrameLossMsgTargetMEPID is not specified else
              an error is returned."
     ::= { wwpLeosTceCfmFrameLossMsgEntry 3 }
     
 wwpLeosTceCfmFrameLossMsgCount OBJECT-TYPE
     SYNTAX       INTEGER (2..600) 
     MAX-ACCESS   read-create
     STATUS       current
     DESCRIPTION
             "This object specifies the FrameLossMeasurementMsg count to be used
              when sending link FrameLossMeasurementMsg."
     ::= { wwpLeosTceCfmFrameLossMsgEntry 4 }
 
 wwpLeosTceCfmFrameLossMsgPriority OBJECT-TYPE
     SYNTAX       INTEGER (0..7)
     MAX-ACCESS   read-create
     STATUS       current
     DESCRIPTION
             "This object specifies the FrameLossMeasurementMsg priority to be
             used when sending link FrameLossMeasurementMsg."
     ::= { wwpLeosTceCfmFrameLossMsgEntry 5 }
 
 wwpLeosTceCfmFrameLossMsgRowStatus OBJECT-TYPE
     SYNTAX       RowStatus
     MAX-ACCESS   read-only
     STATUS       current
     DESCRIPTION
             "This object is a read-only field. A row in this table is system-generated 
             on creation of CFM service and CFM mep objects."
     ::= { wwpLeosTceCfmFrameLossMsgEntry 6 }

  wwpLeosTceCfmFrameLossMsgRepeatInterval OBJECT-TYPE
     SYNTAX       Unsigned32 (0..1440)
     UNITS		  "minutes"
     MAX-ACCESS   read-create
     STATUS       current
     DESCRIPTION
             "This object represents the Transmission Interval for the Frame loss messages"
     ::= { wwpLeosTceCfmFrameLossMsgEntry 50 }
 
 wwpLeosTceCfmFrameLossMsgNearLossThreshold OBJECT-TYPE
     SYNTAX       INTEGER (0..600)
     MAX-ACCESS   read-create
     STATUS       current
     DESCRIPTION
             "This object represents the threshold value for the near-end frame loss"
     ::= { wwpLeosTceCfmFrameLossMsgEntry 51 }
 
 wwpLeosTceCfmFrameLossMsgFarLossThreshold OBJECT-TYPE
     SYNTAX       INTEGER (0..600)
     MAX-ACCESS   read-create
     STATUS       current
     DESCRIPTION
             "This object represents the threshold value for the far-end frame loss"
     ::= { wwpLeosTceCfmFrameLossMsgEntry 52 }

  wwpLeosTceCfmFrameLossMsgServiceName OBJECT-TYPE
     SYNTAX       DisplayString (SIZE(1..41))
     MAX-ACCESS   read-only
     STATUS       current
     DESCRIPTION
             "This object specifies the service to be used when
 	sending FrameLossMsg (LMM)."
     ::= { wwpLeosTceCfmFrameLossMsgEntry 53 }
 
 wwpLeosTceCfmFrameLossMsgSubPortName OBJECT-TYPE
     SYNTAX       DisplayString (SIZE(1..31))
     MAX-ACCESS   read-only
     STATUS       current
     DESCRIPTION
             "This object specifies the sub-port name to be used when
 	sending FrameLossMsg (LMM)."
     ::= { wwpLeosTceCfmFrameLossMsgEntry 54 }
 
 wwpLeosTceCfmFrameLossMsgFrameLossNear OBJECT-TYPE
     SYNTAX       Unsigned32
     MAX-ACCESS   read-only
     STATUS       current
     DESCRIPTION
             "This object represents the near-end Frame Loss. For a MEP,
             near-end Frame loss refers to frame loss associated with the
             ingress data frames."
     ::= { wwpLeosTceCfmFrameLossMsgEntry 55 }

wwpLeosTceCfmFrameLossMsgFrameLossFar OBJECT-TYPE
     SYNTAX       Unsigned32
     MAX-ACCESS   read-only
     STATUS       current
     DESCRIPTION
             "This object represents the far-end Frame Loss. For a MEP,
             far-end Frame loss refers to frame loss associated with the
             egress data frames."
     ::= { wwpLeosTceCfmFrameLossMsgEntry 56 }

wwpLeosTceCfmFrameLossMsgTotalTxLmm OBJECT-TYPE
     SYNTAX       Unsigned32
     MAX-ACCESS   read-only
     STATUS       current
     DESCRIPTION
             "This object represents the total LMMs transmitted."
     ::= { wwpLeosTceCfmFrameLossMsgEntry 57 }

wwpLeosTceCfmFrameLossMsgTotalRxLmm OBJECT-TYPE
     SYNTAX       Unsigned32
     MAX-ACCESS   read-only
     STATUS       current
     DESCRIPTION
             "This object represents the total LMMs received."
     ::= { wwpLeosTceCfmFrameLossMsgEntry 58 } 
     
 wwpLeosTceCfmFrameLossMsgTotalTxLmr OBJECT-TYPE
     SYNTAX       Unsigned32
     MAX-ACCESS   read-only
     STATUS       current
     DESCRIPTION
             "This object represents the total LMRs transmitted"
     ::= { wwpLeosTceCfmFrameLossMsgEntry 59 }
 
 wwpLeosTceCfmFrameLossMsgTotalRxLmr OBJECT-TYPE
     SYNTAX       Unsigned32
     MAX-ACCESS   read-only
     STATUS       current
     DESCRIPTION
             "This object represents the total LMRs received"
     ::= { wwpLeosTceCfmFrameLossMsgEntry 60 }      
     
  wwpLeosTceCfmFrameLossMsgAction OBJECT-TYPE
     SYNTAX       SendState
     MAX-ACCESS   read-create
     STATUS       current
     DESCRIPTION
             "This object represents the action for the message (send, clear or cancel)."
     ::= { wwpLeosTceCfmFrameLossMsgEntry 61 }

 --
 -- CFM Fault trap control
 --    
 wwpLeosCfmFaultTrapState OBJECT-TYPE
     SYNTAX       INTEGER {
     				disabled(1),
     				enabled(2)
     				}
     MAX-ACCESS   read-write
     STATUS       current
     DESCRIPTION
             "Setting this object to 'disabled' causes
              CFM fault traps to be suppressed." 
     DEFVAL { enabled }
     ::= { wwpLeosCfmFaultNotif 1 }     
      
 --
 -- Notifications
 --  
 wwpLeosCfmFaultTrap  NOTIFICATION-TYPE
    OBJECTS {
                        wwpLeosCfmServiceName,
                        wwpLeosCfmServiceVlan,
                        wwpLeosCfmServiceMdLevel,
                        wwpLeosCfmServiceFaultTime, 
                        wwpLeosCfmServiceFaultType,
                        wwpLeosCfmServiceFaultDesc,
                        wwpLeosCfmServiceFaultMep                        
                        }
        STATUS  current
        DESCRIPTION
                "A notification is sent whenever the fault is detected."
        ::= { wwpLeosCfmNotifMIBNotification 1 }

 wwpLeosCfmPbtFaultTrap  NOTIFICATION-TYPE
        OBJECTS {
                        wwpLeosCfmServiceName,
                        wwpLeosCfmServiceType,
                        wwpLeosCfmServiceValue,
                        wwpLeosCfmServiceAdminState,
                        wwpLeosCfmServiceOperState,
                        wwpLeosCfmServiceFaultTime, 
                        wwpLeosCfmServiceFaultType,
                        wwpLeosCfmServiceFaultDesc                                                
                        }
        STATUS     deprecated
        DESCRIPTION
                "A notification is sent whenever the fault is detected for a PBT tunnel.
                 wwpLeosCfmServiceType is always set to pbtTunnel."
        ::= { wwpLeosCfmNotifMIBNotification 2 }        
        
 wwpLeosCfmDelayFaultTrap  NOTIFICATION-TYPE
        OBJECTS {
                        wwpLeosCfmServiceName,
                        wwpLeosCfmServiceVlan,
                        wwpLeosCfmRemoteMEPDelay,
                        wwpLeosCfmDelayMsgDelayThreshold
                }
        STATUS	   current
        DESCRIPTION
        "A notification is sent whenever the fault is detected during
         a Delay Measurement test with a fault threshold."
        ::= { wwpLeosCfmNotifMIBNotification 3 }   
 
 wwpLeosCfmJitterFaultTrap  NOTIFICATION-TYPE
 	OBJECTS {
        		wwpLeosCfmServiceName,
        		wwpLeosCfmServiceVlan,
        		wwpLeosCfmRemoteMEPJitter,
        		wwpLeosCfmDelayMsgJitterThreshold        				        				
		   	}
	STATUS	   current
	DESCRIPTION
		"A notification is sent whenever the fault is detected during
		a Delay Measurement test with a fault threshold."
	::= { wwpLeosCfmNotifMIBNotification 4 }   

 wwpLeosCfmFrameLossNearFaultTrap  NOTIFICATION-TYPE
 	OBJECTS {
        		wwpLeosCfmServiceName,
        		wwpLeosCfmServiceVlan,
        		wwpLeosCfmRemoteMEPFrameLossNear,
        		wwpLeosCfmFrameLossMsgFlnThreshold        				        				
		   	}
	STATUS	   current
	DESCRIPTION
		"A notification is sent whenever the fault is detected during
		a Frame Loss Measurement test with a fault threshold."
	::= { wwpLeosCfmNotifMIBNotification 5 }   
 
 wwpLeosCfmFrameLossFarFaultTrap  NOTIFICATION-TYPE
 	OBJECTS {
        		wwpLeosCfmServiceName,
        		wwpLeosCfmServiceVlan,
        		wwpLeosCfmRemoteMEPFrameLossFar,
        		wwpLeosCfmFrameLossMsgFlfThreshold        				        				
		   	}
	STATUS	   current
	DESCRIPTION
		"A notification is sent whenever the fault is detected during
		a Frame Loss Measurement test with a fault threshold."
	::= { wwpLeosCfmNotifMIBNotification 6 } 
	
wwpLeosCfmExtDelayFaultTrap  NOTIFICATION-TYPE
 	OBJECTS {
        		wwpLeosCfmServiceName,
        		wwpLeosCfmServiceVlan,
        		wwpLeosCfmRemoteMEPDelay,
        		wwpLeosCfmExtDelayMsgDelayThreshold        				        				
		   	}
	STATUS	   current
	DESCRIPTION
		"A notification is sent whenever the fault is detected during
		a Delay Measurement test with a fault threshold."
	::= { wwpLeosCfmNotifMIBNotification 7 }   
 
 wwpLeosCfmExtJitterFaultTrap  NOTIFICATION-TYPE
 	OBJECTS {
        		wwpLeosCfmServiceName,
        		wwpLeosCfmServiceVlan,
        		wwpLeosCfmRemoteMEPJitter,
        		wwpLeosCfmExtDelayMsgJitterThreshold        				        				
		   	}
	STATUS	   current
	DESCRIPTION
		"A notification is sent whenever the fault is detected during
		a Delay Measurement test with a fault threshold."
	::= { wwpLeosCfmNotifMIBNotification 8 }   

 wwpLeosCfmExtFrameLossNearFaultTrap  NOTIFICATION-TYPE
 	OBJECTS {
        		wwpLeosCfmServiceName,
        		wwpLeosCfmServiceVlan,
        		wwpLeosCfmRemoteMEPFrameLossNear,
        		wwpLeosCfmExtFrameLossMsgFlnThreshold        				        				
		   	}
	STATUS	   current
	DESCRIPTION
		"A notification is sent whenever the fault is detected during
		a Frame Loss Measurement test with a fault threshold."
	::= { wwpLeosCfmNotifMIBNotification 9 }   
 
 wwpLeosCfmExtFrameLossFarFaultTrap  NOTIFICATION-TYPE
 	OBJECTS {
        		wwpLeosCfmServiceName,
        		wwpLeosCfmServiceVlan,
        		wwpLeosCfmRemoteMEPFrameLossFar,
        		wwpLeosCfmExtFrameLossMsgFlfThreshold        				        				
		   	}
	STATUS	   current
	DESCRIPTION
		"A notification is sent whenever the fault is detected during
		a Frame Loss Measurement test with a fault threshold."
	::= { wwpLeosCfmNotifMIBNotification 20 }   
 
 wwpLeosCfmExtFaultTrapSet  NOTIFICATION-TYPE
        OBJECTS      {
          		wwpLeosCfmServiceName,                                      
          		wwpLeosCfmServiceType,
          		wwpLeosCfmServiceValue,
          		wwpLeosCfmServiceAdminState,                 
          		wwpLeosCfmServiceOperState,
          		wwpLeosCfmServiceMdLevel,                 
          		wwpLeosCfmServiceFaultTime, 
          		wwpLeosCfmServiceFaultType,
          		wwpLeosCfmServiceFaultDesc,
          		wwpLeosCfmServiceFaultMep,
          		cienaGlobalSeverity,
          		cienaGlobalMacAddress
       }
   STATUS      current
   DESCRIPTION
      "A notification is sent whenever the fault is detected."
   ::= { wwpLeosCfmNotifMIBNotification 21 }

 wwpLeosCfmExtFaultTrapClear  NOTIFICATION-TYPE
        OBJECTS      {
          		wwpLeosCfmServiceName,
          		wwpLeosCfmServiceType,        				        				
        		wwpLeosCfmServiceValue,
        		wwpLeosCfmServiceAdminState,                 
                wwpLeosCfmServiceOperState,
  		        wwpLeosCfmServiceMdLevel,     				
	            wwpLeosCfmServiceFaultTime, 
                wwpLeosCfmServiceFaultType,
                wwpLeosCfmServiceFaultDesc,
                wwpLeosCfmServiceFaultMep,
                cienaGlobalSeverity,
                cienaGlobalMacAddress
      }
   STATUS      current
   DESCRIPTION
      "A notification is sent whenever the fault is resolved and cleared."
   ::= { wwpLeosCfmNotifMIBNotification 22 }   
 
 wwpLeosCfmBadSequenceFaultTrap   NOTIFICATION-TYPE
 		OBJECTS { 
 				wwpLeosCfmServiceName,
        		wwpLeosCfmServiceVlan,  
        		wwpLeosCfmExtMEPLMMBadSequence,
        	 	wwpLeosCfmExtFrameLossMsgSeqThreshold     
        	 	}
 		STATUS      current
   		DESCRIPTION
      		"A notification is sent whenever wwpLeosCfmExtMEPLMMBadSequence exceeds wwpLeosCfmExtFrameLossMsgSeqThreshold 
      		in a Frame Loss Measurement test."
   ::= { wwpLeosCfmNotifMIBNotification 23 }
   
 wwpLeosCfmBlockOppositeMEPSetTrap	NOTIFICATION-TYPE
 	OBJECTS {
 				sysName,
 				wwpLeosCfmServiceMdLevel,
 				wwpLeosCfmServiceCfmMAID,
 				wwpLeosCfmExtMEPId,
 				wwpLeosCfmExtVlanId,
 				wwpLeosCfmExtMEPTagVID,
 				wwpLeosCfmExtMEPBlockOppositeFaultCurrent,
 				cienaGlobalSeverity,
 				cienaGlobalMacAddress
 			}
 	STATUS	current
 	DESCRIPTION "A notification sent whenever the number of frames blocked by the presence
 				of a MEP of the opposite type exceeds the threshold during the sample window."
 	::= { wwpLeosCfmNotifMIBNotification 24 }
 
  wwpLeosCfmBlockOppositeMEPClearTrap	NOTIFICATION-TYPE
 	OBJECTS {
 				sysName,
 				wwpLeosCfmServiceMdLevel,
 				wwpLeosCfmServiceCfmMAID,
 				wwpLeosCfmExtMEPId,
 				wwpLeosCfmExtVlanId,
 				wwpLeosCfmExtMEPTagVID,
 				cienaGlobalSeverity,
 				cienaGlobalMacAddress
 			}
 	STATUS	current
 	DESCRIPTION "A notification sent whenever the number of frames blocked by the presence
 				of a MEP of the opposite type drops below the threshold during the sample window."
 	::= { wwpLeosCfmNotifMIBNotification 25 }    
 	
  wwpLeosCfmExtSynLossSessionNearFaultTrap   NOTIFICATION-TYPE
     OBJECTS {
        		wwpLeosCfmServiceName,
        		wwpLeosCfmServiceVlan,        	
        		wwpLeosCfmExtSynLossSessionFrameLossNear,
        		wwpLeosCfmExtSynLossSessionFlnThreshold,
        		cienaGlobalSeverity,
        		cienaGlobalMacAddress,
                wwpLeosCfmExtSynLossSessionPriority,
                wwpLeosCfmExtSynLossSessionTestId
		   	}
	STATUS	   current
	DESCRIPTION
		"A notification is sent whenever the fault is detected during
		a Synthetic Loss Measurement test with a near loss threshold fault."
	::= { wwpLeosCfmNotifMIBNotification 26}  
	
  wwpLeosCfmExtSynLossSessionFarFaultTrap   NOTIFICATION-TYPE
     OBJECTS {
        		wwpLeosCfmServiceName,
        		wwpLeosCfmServiceVlan,
        		wwpLeosCfmExtSynLossSessionFrameLossFar,
        		wwpLeosCfmExtSynLossSessionFlfThreshold,
        		cienaGlobalSeverity,
        		cienaGlobalMacAddress,
                wwpLeosCfmExtSynLossSessionPriority,
                wwpLeosCfmExtSynLossSessionTestId
		   	}
	STATUS	   current
	DESCRIPTION
		"A notification is sent whenever the fault is detected during
		a Synthetic Loss Measurement test with a far loss threshold fault."
	::= { wwpLeosCfmNotifMIBNotification 27}  	
   
   wwpLeosCfmExtSynLossSessionNearFaultClearTrap   NOTIFICATION-TYPE
     OBJECTS {
        		wwpLeosCfmServiceName,
        		wwpLeosCfmServiceVlan,        	
        		wwpLeosCfmExtSynLossSessionFrameLossNear,
        		wwpLeosCfmExtSynLossSessionFlnThreshold,
        		cienaGlobalSeverity,
        		cienaGlobalMacAddress,
                wwpLeosCfmExtSynLossSessionPriority,
                wwpLeosCfmExtSynLossSessionTestId
		   	}
	STATUS	   current
	DESCRIPTION
		"A notification is sent whenever the fault is cleared during
		a Synthetic Loss Measurement test with a near loss threshold fault."
	::= { wwpLeosCfmNotifMIBNotification 28}  
	
  wwpLeosCfmExtSynLossSessionFarFaultClearTrap   NOTIFICATION-TYPE
     OBJECTS {
        		wwpLeosCfmServiceName,
        		wwpLeosCfmServiceVlan,
        		wwpLeosCfmExtSynLossSessionFrameLossFar,
        		wwpLeosCfmExtSynLossSessionFlfThreshold,
        		cienaGlobalSeverity,
        		cienaGlobalMacAddress,
                wwpLeosCfmExtSynLossSessionPriority,
                wwpLeosCfmExtSynLossSessionTestId
		   	}
	STATUS	   current
	DESCRIPTION
		"A notification is sent whenever the fault is cleared during
		a Synthetic Loss Measurement test with a far loss threshold fault."
	::= { wwpLeosCfmNotifMIBNotification 29}  	

  wwpLeosCfmExtDelaySessionAvgDelayFaultSetTrap  NOTIFICATION-TYPE
 	OBJECTS {
        		wwpLeosCfmServiceName,
        		wwpLeosCfmServiceVlan,
        		wwpLeosCfmExtDelaySessionAvgDelay,
        		wwpLeosCfmExtDelaySessionDelayThreshold,
        		cienaGlobalSeverity,
        		cienaGlobalMacAddress        				        				
		   	}
	STATUS	   current
	DESCRIPTION
		"A notification is sent when the average delay exceeds the configured delay threshold value."
	::= { wwpLeosCfmNotifMIBNotification 30 }  
	
 wwpLeosCfmExtDelaySessionAvgDelayFaultClearTrap  NOTIFICATION-TYPE
 	OBJECTS {
        		wwpLeosCfmServiceName,
        		wwpLeosCfmServiceVlan,
        		wwpLeosCfmExtDelaySessionAvgDelay,
        		wwpLeosCfmExtDelaySessionDelayThreshold,
        		cienaGlobalSeverity,
        		cienaGlobalMacAddress        				        				
		   	}
	STATUS	   current
	DESCRIPTION
		"A notification is sent when the average delay is back to normal based on the configured delay threshold value."
	::= { wwpLeosCfmNotifMIBNotification 31 }   	 
 
 wwpLeosCfmExtDelaySessionAvgJitterFaultSetTrap  NOTIFICATION-TYPE
 	OBJECTS {
        		wwpLeosCfmServiceName,
        		wwpLeosCfmServiceVlan,
        		wwpLeosCfmExtDelaySessionAvgJitter,
        		wwpLeosCfmExtDelaySessionJitterThreshold,
        		cienaGlobalSeverity,
        		cienaGlobalMacAddress          				        				
		   	}
	STATUS	   current
	DESCRIPTION
		"A notification is sent when the average jitter exceeds the configured jitter threshold value."
	::= { wwpLeosCfmNotifMIBNotification 32 }   
 
 wwpLeosCfmExtDelaySessionAvgJitterFaultClearTrap  NOTIFICATION-TYPE
 	OBJECTS {
        		wwpLeosCfmServiceName,
        		wwpLeosCfmServiceVlan,
        		wwpLeosCfmExtDelaySessionAvgJitter,
        		wwpLeosCfmExtDelaySessionJitterThreshold,
        		cienaGlobalSeverity,
        		cienaGlobalMacAddress          				        				
		   	}
	STATUS	   current
	DESCRIPTION
		"A notification is sent when the average jitter is back to normal based on the configured jitter threshold value."
	::= { wwpLeosCfmNotifMIBNotification 33 }  

 wwpLeosCfmExtDelaySessionMaxDelayFaultSetTrap  NOTIFICATION-TYPE
 	OBJECTS {
        		wwpLeosCfmServiceName,
        		wwpLeosCfmServiceVlan,
        		wwpLeosCfmExtDelaySessionMaxDelay,
        		wwpLeosCfmExtDelaySessionMaxDelayThreshold,
        		cienaGlobalSeverity,
        		cienaGlobalMacAddress        				        				
		   	}
	STATUS	   current
	DESCRIPTION
		"A notification is sent when the maximum delay exceeds the configured maximum delay threshold value."
	::= { wwpLeosCfmNotifMIBNotification 34 }  
	
 wwpLeosCfmExtDelaySessionMaxDelayFaultClearTrap  NOTIFICATION-TYPE
 	OBJECTS {
        		wwpLeosCfmServiceName,
        		wwpLeosCfmServiceVlan,
        		wwpLeosCfmExtDelaySessionMaxDelay,
        		wwpLeosCfmExtDelaySessionMaxDelayThreshold,
        		cienaGlobalSeverity,
        		cienaGlobalMacAddress        				        				
		   	}
	STATUS	   current
	DESCRIPTION
		"A notification is sent when the maximum delay is back to normal based on the configured maximum delay threshold value."
	::= { wwpLeosCfmNotifMIBNotification 35 }   	 
 
 wwpLeosCfmExtDelaySessionMaxJitterFaultSetTrap  NOTIFICATION-TYPE
 	OBJECTS {
        		wwpLeosCfmServiceName,
        		wwpLeosCfmServiceVlan,
        		wwpLeosCfmExtDelaySessionMaxJitter,
        		wwpLeosCfmExtDelaySessionMaxJitterThreshold,
        		cienaGlobalSeverity,
        		cienaGlobalMacAddress          				        				
		   	}
	STATUS	   current
	DESCRIPTION
		"A notification is sent when the maximum jitter exceeds the configured maximum jitter threshold value."
	::= { wwpLeosCfmNotifMIBNotification 36 }   
 
 wwpLeosCfmExtDelaySessionMaxJitterFaultClearTrap  NOTIFICATION-TYPE
 	OBJECTS {
        		wwpLeosCfmServiceName,
        		wwpLeosCfmServiceVlan,
        		wwpLeosCfmExtDelaySessionMaxJitter,
        		wwpLeosCfmExtDelaySessionMaxJitterThreshold,
        		cienaGlobalSeverity,
        		cienaGlobalMacAddress          				        				
		   	}
	STATUS	   current
	DESCRIPTION
		"A notification is sent when the maximum jitter is back to normal based on the configured maximum jitter threshold value."
	::= { wwpLeosCfmNotifMIBNotification 37 }  

 wwpLeosCfmExtFrameLossSessionFrameLossNearFaultSetTrap  NOTIFICATION-TYPE
 	OBJECTS {
        		wwpLeosCfmServiceName,
        		wwpLeosCfmServiceVlan,
        		wwpLeosCfmExtFrameLossSessionFrameLossNear,
        		wwpLeosCfmExtFrameLossSessionFrameLossNearThreshold,
        		cienaGlobalSeverity,
        		cienaGlobalMacAddress        				        				
		   	}
	STATUS	   current
	DESCRIPTION
		"A notification is sent when the frame loss near value exceeds the configured threshold value."
	::= { wwpLeosCfmNotifMIBNotification 38 }   
 
 wwpLeosCfmExtFrameLossSessionFrameLossNearFaultClearTrap  NOTIFICATION-TYPE
 	OBJECTS {
        		wwpLeosCfmServiceName,
        		wwpLeosCfmServiceVlan,
        		wwpLeosCfmExtFrameLossSessionFrameLossNear,
        		wwpLeosCfmExtFrameLossSessionFrameLossNearThreshold,
        		cienaGlobalSeverity,
        		cienaGlobalMacAddress        				        				
		   	}
	STATUS	   current
	DESCRIPTION
		"A notification is sent when the frame loss near value is back to normal based on the configured threshold value."
	::= { wwpLeosCfmNotifMIBNotification 39 }
	  
 wwpLeosCfmExtFrameLossSessionFrameLossFarFaultSetTrap  NOTIFICATION-TYPE
 	OBJECTS {
        		wwpLeosCfmServiceName,
        		wwpLeosCfmServiceVlan,
        		wwpLeosCfmExtFrameLossSessionFrameLossFar,
        		wwpLeosCfmExtFrameLossSessionFrameLossFarThreshold,
        		cienaGlobalSeverity,
        		cienaGlobalMacAddress        				        				
		   	}
	STATUS	   current
	DESCRIPTION
		"A notification is sent when the frame loss far value exceeds the configured threshold value."
	::= { wwpLeosCfmNotifMIBNotification 40 }      
 
 wwpLeosCfmExtFrameLossSessionFrameLossFarFaultClearTrap  NOTIFICATION-TYPE
 	OBJECTS {
        		wwpLeosCfmServiceName,
        		wwpLeosCfmServiceVlan,
        		wwpLeosCfmExtFrameLossSessionFrameLossFar,
        		wwpLeosCfmExtFrameLossSessionFrameLossFarThreshold,
        		cienaGlobalSeverity,
        		cienaGlobalMacAddress        				        				
		   	}
	STATUS	   current
	DESCRIPTION
		"A notification is sent when the frame loss far value is back to normal based on the configured threshold value."
	::= { wwpLeosCfmNotifMIBNotification 41 }    
	
 wwpLeosCfmFrameLossSessionBadSequenceTrap   NOTIFICATION-TYPE
 		OBJECTS { 
 				wwpLeosCfmServiceName,
        		wwpLeosCfmServiceVlan,  
        		wwpLeosCfmExtMEPLMMBadSequence,
        	 	wwpLeosCfmExtFrameLossSessionSeqThreshold,
        	 	cienaGlobalSeverity,
        	 	cienaGlobalMacAddress     
        	 	}
 		STATUS      current
   		DESCRIPTION
      		"A notification is sent whenever wwpLeosCfmExtMEPLMMBadSequence exceeds wwpLeosCfmExtFrameLossSessionSeqThreshold 
      		in a Frame Loss Measurement test."
   ::= { wwpLeosCfmNotifMIBNotification 42 }

 wwpLeosCfmServiceCsfFaultSetTrap   NOTIFICATION-TYPE
 		OBJECTS { 
 				wwpLeosCfmServiceMdLevel,
 				wwpLeosCfmServiceName,
 				wwpLeosCfmServiceFaultMep,
 				wwpLeosCfmExtMEPCSFRxFaultType,
 				cienaGlobalSeverity,
 				cienaGlobalMacAddress
        	 	}
 		STATUS      current
   		DESCRIPTION
      		"A notification is sent whenever CSF Rx Fault is observed."
   ::= { wwpLeosCfmNotifMIBNotification 43 }

 wwpLeosCfmServiceCsfFaultClearTrap   NOTIFICATION-TYPE
 		OBJECTS { 
 				wwpLeosCfmServiceMdLevel,
 				wwpLeosCfmServiceName,
 				wwpLeosCfmServiceFaultMep,
 				wwpLeosCfmExtMEPCSFRxFaultType,
 				cienaGlobalSeverity,
 				cienaGlobalMacAddress
        	 	}
 		STATUS      current
   		DESCRIPTION
      		"A notification is sent whenever CSF Fault is cleared."
   ::= { wwpLeosCfmNotifMIBNotification 44 }

 wwpLeosCfmExtSynLossSessionSignalDegradeFaultSetTrap   NOTIFICATION-TYPE
 		OBJECTS { 
 				wwpLeosCfmServiceName,
 				wwpLeosCfmServiceVlan,
 				wwpLeosCfmExtFrameLossSessionFrameLossNear,
 				wwpLeosCfmExtFrameLossSessionFrameLossFar,
 				wwpLeosCfmExtSynLossSessionSdSetThreshold,
 				cienaGlobalSeverity,
 				cienaGlobalMacAddress
        	 	}
 		STATUS      current
   		DESCRIPTION
      		"A notification is sent whenever the signal degrade fault is detected during
     		 a Synthetic Loss Measurement test."
   ::= { wwpLeosCfmNotifMIBNotification 45}

 wwpLeosCfmExtSynLossSessionSignalDegradeFaultClearTrap   NOTIFICATION-TYPE
 		OBJECTS { 
 				wwpLeosCfmServiceName,
 				wwpLeosCfmServiceVlan,
 				wwpLeosCfmExtFrameLossSessionFrameLossNear,
 				wwpLeosCfmExtFrameLossSessionFrameLossFar,
 				wwpLeosCfmExtSynLossSessionSdClearThreshold,
 				cienaGlobalSeverity,
 				cienaGlobalMacAddress
        	 	}
 		STATUS      current
   		DESCRIPTION
    		"A notification is sent whenever the signal degrade fault is cleared during
    		 a Synthetic Loss Measurement test."
   ::= { wwpLeosCfmNotifMIBNotification 46}

 wwpLeosCfmExtDelaySessionSignalDegradeFaultSetTrap   NOTIFICATION-TYPE
                OBJECTS {
                                wwpLeosCfmServiceName,
                                wwpLeosCfmServiceVlan,
                                wwpLeosCfmExtDelaySessionBackwardAvgJitter,
                                wwpLeosCfmExtDelaySessionAvgDelay,
                                wwpLeosCfmExtDelaySessionSdJitterSetThreshold,
                                wwpLeosCfmExtDelaySessionSdDelaySetThreshold,
                                cienaGlobalSeverity,
                                cienaGlobalMacAddress
                        }
                STATUS      current
                DESCRIPTION
                "A notification is sent whenever the signal degrade fault is detected during
                 a Delay Measurement test."
   ::= { wwpLeosCfmNotifMIBNotification 47}

 wwpLeosCfmExtDelaySessionSignalDegradeFaultClearTrap   NOTIFICATION-TYPE
                OBJECTS {
                                wwpLeosCfmServiceName,
                                wwpLeosCfmServiceVlan,
                                wwpLeosCfmExtDelaySessionBackwardAvgJitter,
                                wwpLeosCfmExtDelaySessionAvgDelay,
                                wwpLeosCfmExtDelaySessionSdJitterClearThreshold,
                                wwpLeosCfmExtDelaySessionSdDelayClearThreshold,
                                cienaGlobalSeverity,
                                cienaGlobalMacAddress
                        }
                STATUS      current
                DESCRIPTION
                "A notification is sent whenever the signal degrade fault is cleared during
                 a Delay Measurement test."
   ::= { wwpLeosCfmNotifMIBNotification 48}

 --
 -- TCE Notifications
 --  
 wwpLeosCfmFaultTrapSet  NOTIFICATION-TYPE
        OBJECTS      {
          wwpLeosCfmServiceName,                                      
          wwpLeosCfmServiceType,
          wwpLeosCfmServiceValue,
          wwpLeosCfmServiceAdminState,                 
          wwpLeosCfmServiceOperState,
          wwpLeosCfmServiceMdLevel,                 
          wwpLeosCfmServiceFaultTime, 
          wwpLeosCfmServiceFaultType,
          wwpLeosCfmServiceFaultDesc,
          wwpLeosCfmServiceFaultMep,
          wwpLeosCfmServiceVsPbtName
       }
   STATUS      current
   DESCRIPTION
      "A notification is sent whenever the fault is detected."
   ::= { wwpLeosCfmNotifMIBNotification 10 }

 wwpLeosCfmFaultTrapClear  NOTIFICATION-TYPE
        OBJECTS      {
          wwpLeosCfmServiceName,                                      
          wwpLeosCfmServiceType,
          wwpLeosCfmServiceValue,
          wwpLeosCfmServiceAdminState,                 
          wwpLeosCfmServiceOperState,
          wwpLeosCfmServiceMdLevel,
          wwpLeosCfmServiceVsPbtName
       }
   STATUS      current
   DESCRIPTION
      "A notification is sent whenever the fault is resolved and cleared."
   ::= { wwpLeosCfmNotifMIBNotification 11 }
  
  wwpLeosCfmDmmTrap  NOTIFICATION-TYPE
        OBJECTS      {
          wwpLeosTceCfmDelayMsgServiceName,                                      
          wwpLeosTceCfmDelayMsgLocalMEPId,
          --wwpLeosTceCfmDelayMsgTargetMacAddr,                 
          wwpLeosTceCfmDelayMsgDelayThreshold,
          wwpLeosTceCfmDelayMsgDelay,
          wwpLeosTceCfmDelayMsgJitterThreshold,
          wwpLeosTceCfmDelayMsgJitter,
          wwpLeosTceCfmDelayMsgMaxJitterThreshold,
          wwpLeosTceCfmDelayMsgMaxJitter,
          wwpLeosTceCfmDelayMsgMaxDelayThreshold,
          wwpLeosTceCfmDelayMsgMaxDelay
          
                 }
   STATUS      current
   DESCRIPTION
      "A notification is sent whenever delay average goes above delay-threshold during a delay measurement test, 
      also generated when delay average goes below threshold after going up as a clearing event. 
      Same notification is generated whenever the average jitter goes above Jitter threshold during a delay measurement test
      and when the maximum delay and jitter go above the maximum delay and jitter thresholds respectively.
      Also generated when jitter average goes below jitter threshold after going up as a clearing event.
      When jitter event is generated, wwpLeosTceCfmDelayMsgDelayThreshold and wwpLeosTceCfmDelayMsgDelay
      varbind values are set to 0. Similarly when max delay event is generated wwpLeosTceCfmDelayMsgMaxJitter and
      wwpLeosTceCfmDelayMsgMaxJitterThreshold are set to 0 and vice versa"
   ::= { wwpLeosCfmNotifMIBNotification 12 }
  
  wwpLeosCfmLmmTrap  NOTIFICATION-TYPE
        OBJECTS      {
          wwpLeosTceCfmFrameLossMsgServiceName,                                      
          wwpLeosTceCfmFrameLossMsgLocalMEPId,
          --wwpLeosTceCfmFrameLossMsgTargetMacAddr,                 
          wwpLeosTceCfmFrameLossMsgNearLossThreshold,
          wwpLeosTceCfmFrameLossMsgFrameLossNear,
          wwpLeosTceCfmFrameLossMsgFarLossThreshold,
          wwpLeosTceCfmFrameLossMsgFrameLossFar
          
                 }
   STATUS      current
   DESCRIPTION
      "A notification is sent whenever FrameLoss Near average goes above FrameLoss Near threshold during a 
      Frame Loss measurement test. Also generated when FrameLoss Near average goes below FrameLoss Near threshold 
      after going up as a clearing event. 
      Same notification is generated whenever FrameLoss Far Average goes above Frameloss Far threshold value during a 
      Frame Loss measurement test. Also generated when Frameloss Far average goes below Frameloss Far threshold after going up
      as a clearing event. 
      When FrameLoss Near event is generated wwpLeosTceCfmFrameLossMsgFrameLossFar and  
      wwpLeosTceCfmFrameLossMsgFarLossThreshold varbind values are 0"
   ::= { wwpLeosCfmNotifMIBNotification 13 }

 --
 -- Add groups into the table
 --
 --

 END
