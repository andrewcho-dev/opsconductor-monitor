-- This file was included in WWP MIB release 04-21-05-0007
 --
 -- WWP-LEOS-TACACS-CLIENT-MIB.my
 --
 --

 WWP-LEOS-TACACS-CLIENT-MIB DEFINITIONS ::= BEGIN

 IMPORTS
   IpAddress, Integer32, Counter32, Gauge32, OBJECT-TYPE, MODULE-IDENTITY, NOTIFICATION-TYPE
       FROM SNMPv2-SMI
   DisplayString, RowStatus, TruthValue, TEXTUAL-CONVENTION
       FROM SNMPv2-TC
   InetAddressType,InetAddress
        FROM INET-ADDRESS-MIB
   wwpModulesLeos
       FROM WWP-SMI
   PreferredSourceAddress
       FROM CIENA-CES-MGMT-INTERFACE-MIB;


 wwpLeosTacacsClientMIB MODULE-IDENTITY
            LAST-UPDATED "201711150000Z"
            ORGANIZATION "Ciena Corp."
            CONTACT-INFO
               "   Mib Meister
                   7035 Ridge Road
                   Hanover, Maryland 21076
                   USA
                   Phone:  +1 800 921 1144
                   Email:  support@ciena.com"
            DESCRIPTION
               "The MIB module for the WWP TACACS Server specific configuration
                and monitoring information."

            REVISION     "201711150000Z"
            DESCRIPTION
               "Updated contact info."
            REVISION "201706220000Z"
            DESCRIPTION
               "Added wwpLeosTacacsClientPreferredSourceAddress"

            REVISION "201604010000Z"
            DESCRIPTION
               "Added the wwpLeosTacacsClientConnectionFailed notification."

            REVISION "201602220000Z"
            DESCRIPTION
                     "Deprecated wwpLeosTacacsClientServerApplication, wwpLeosTacacsClientAuthenticationServerApplication,
                      wwpLeosTacacsClientAuthorizationServerApplication, and wwpLeosTacacsClientAccountingServerApplication,
                      all of which were unused."
            REVISION "201507220000Z"
            DESCRIPTION
                     "Changed the TACACS authentication string range to accept a zero length string."
            REVISION "201506220000Z"
            DESCRIPTION
                     "Added wwpLeosTacacsClientAuthSecret."
            REVISION "201504150000Z"
            DESCRIPTION
                    "Added wwpLeosTacacsAuthenticationEnhancedMultiFactor for enhanced multi-factor authentication"
            REVISION "201406240000Z"
            DESCRIPTION
                    "Corrected range of wwpLeosTacacsClientPrivilegeLevelAdmin from (2..13) to (1..13),
                     and wwpLeosTacacsClientPrivilegeLevelDiag from  (4..15) to (3..15) and fixed default
           for wwpLeosTacacsClientPrivilegeLevelAdmin and wwpLeosTacacsClientPrivilegeLevelRW."
            REVISION    "201304230000Z"
       DESCRIPTION
          "Miscellaneous spelling and description corrections."
       REVISION    "201204050000Z"
       DESCRIPTION
                    "Added wwpLeosTacacsClientServerResolvedInetAddrType,
                     wwpLeosTacacsClientServerResolvedInetAddr,
                     wwpLeosTacacsClientAuthenticationServerResolvedInetAddrType,
                     wwpLeosTacacsClientAuthenticationServerResolvedInetAddr,
                     wwpLeosTacacsClientAuthorizationServerResolvedInetAddrType,
                     wwpLeosTacacsClientAuthorizationServerResolvedInetAddr,
                     wwpLeosTacacsClientAccountingServerResolvedInetAddrType and
                     wwpLeosTacacsClientAccountingServerResolvedInetAddr for inet addressing."
            REVISION    "201108040000Z"
            DESCRIPTION
                    "Deprecated wwpLeosTacacsClientGlobalServers."
       REVISION    "200104031700Z"
       DESCRIPTION
          "Initial creation."
       ::= { wwpModulesLeos 402 }



 TacacsString ::= TEXTUAL-CONVENTION
    DISPLAY-HINT "255a"
    STATUS       current
    DESCRIPTION
            "Uset to repesent the TACACS authentication string"
    SYNTAX       OCTET STRING (SIZE (0 | 2..127))

 --
 -- Node definitions
 --
 
 wwpLeosTacacsClientMIBObjects OBJECT IDENTIFIER ::= { wwpLeosTacacsClientMIB 1 }
 
 wwpLeosTacacsClient OBJECT IDENTIFIER ::= {wwpLeosTacacsClientMIBObjects 1 }

 -- Notifications 
  
 wwpLeosTacacsClientMIBNotificationPrefix  OBJECT IDENTIFIER ::= { wwpLeosTacacsClientMIB 2 } 
 wwpLeosTacacsClientMIBNotifications       OBJECT IDENTIFIER ::=  
                       { wwpLeosTacacsClientMIBNotificationPrefix 0 }

 -- Conformance information 
 
 wwpLeosTacacsClientMIBConformance OBJECT IDENTIFIER ::= { wwpLeosTacacsClientMIB 3 } 
 wwpLeosTacacsClientMIBCompliances OBJECT IDENTIFIER ::= { wwpLeosTacacsClientMIBConformance 1 } 		
 wwpLeosTacacsClientMIBGroups      OBJECT IDENTIFIER ::= { wwpLeosTacacsClientMIBConformance 2 }
			
 
 wwpLeosTacacsAdminState OBJECT-TYPE     
     SYNTAX        INTEGER {
			disabled(1),
			enabled(2)
                   }
     MAX-ACCESS    read-write
     STATUS        current
     DESCRIPTION
	     "Setting this object administratively enables/disables the TACACS client on the device."
     ::= { wwpLeosTacacsClient 1 }

 wwpLeosTacacsOperState OBJECT-TYPE     
     SYNTAX        INTEGER {
			disabled(1),
			enabled(2)
                   }
     MAX-ACCESS    read-only
     STATUS        current
     DESCRIPTION
	     "This object returns the operational state of TACACS client."
     ::= { wwpLeosTacacsClient 2 }

 wwpLeosTacacsClientTimeout OBJECT-TYPE
     SYNTAX       Integer32 (1..30)
     UNITS        "seconds"
     MAX-ACCESS   read-write
     STATUS       current
     DESCRIPTION
	     "This is the time in seconds between retransmissions
	      to the TACACS server."
     DEFVAL { 1 }
     ::= { wwpLeosTacacsClient 3 }
                
 wwpLeosTacacsClientRetries   OBJECT-TYPE
     SYNTAX         Integer32 (0..3)
     MAX-ACCESS     read-write
     STATUS         deprecated
     DESCRIPTION
         "Indicates the number of times the TACACS server should be
          tried before giving up on the server."
     DEFVAL { 3 }
     ::= { wwpLeosTacacsClient 4 } 
 
 wwpLeosTacacsClientPrivilegeLevelRW   OBJECT-TYPE
     SYNTAX         Integer32 (2..14)
     MAX-ACCESS     read-write
     STATUS         current
     DESCRIPTION
	     "Indicates the privilege level used for mapping a range of TACACS 
	     privilege levels to R-W user privilege level.  A privilege level returned
	     by a server is compared to wwpLeosTacacsClientPrivilegeLevelDiag.
	     If the server privilege level is less than wwpLeosTacacsClientPrivilegeLevelDiag 
	     and greater than or equal to the wwpLeosTacacsClientPrivilegeLevelRW, the
	     privilege level is super-user."
     DEFVAL { 10 }
     ::= { wwpLeosTacacsClient 5 } 

 wwpLeosTacacsClientPrivilegeLevelAdmin   OBJECT-TYPE
     SYNTAX         Integer32 (1..13)
     MAX-ACCESS     read-write
     STATUS         current
     DESCRIPTION
	     "Indicates the privilege level used for mapping a range of TACACS
	     privilege levels to Admin user privilege level. A privilege level returned
	     by a server is compared to wwpLeosTacacsClientPrivilegeLevelRW.
	     If the server privilege level is less than wwpLeosTacacsClientPrivilegeLevelRW
	     and greater than or equal to the wwpLeosTacacsClientPrivilegeLevelAdmin, the
	     privilege level is Admin. Not supported on all platforms."
     DEFVAL { 2 }
     ::= { wwpLeosTacacsClient 6 } 

 wwpLeosTacacsClientPrivilegeLevelDiag   OBJECT-TYPE
     SYNTAX         Integer32 (3..15)
     MAX-ACCESS     read-write
     STATUS         current
     DESCRIPTION
	     "Indicates the privilege level used for mapping a range of TACACS
	     privilege levels to Diagnostic user privilege level. A privilege level returned
	     by a server is compared to this value. If server privilege level is greater than
	     or equal to the wwpLeosTacacsClientPrivilegeLevelDiag, the privilege level is diag."
     DEFVAL { 15 }
     ::= { wwpLeosTacacsClient 7 } 

 wwpLeosTacacsClientAuthKey OBJECT-TYPE
     SYNTAX        TacacsString
     MAX-ACCESS    read-write
     STATUS        current
     DESCRIPTION
	     "The authentication key to be used for TACACS servers.
             Retrieving the value of this object via SNMP
             returns an empty string for security reasons."
     ::= { wwpLeosTacacsClient 8 }

 wwpLeosTacacsAuthenticationAdminState OBJECT-TYPE     
     SYNTAX        INTEGER {
			disabled(1),
			enabled(2)
                   }
     MAX-ACCESS    read-write
     STATUS        current
     DESCRIPTION
	     "Setting this object administratively enables/disables TACACS authentication on the device."
     DEFVAL { enabled }
     ::= { wwpLeosTacacsClient 9 }

 wwpLeosTacacsAuthorizationAdminState OBJECT-TYPE     
     SYNTAX        INTEGER {
			disabled(1),
			enabled(2)
                   }
     MAX-ACCESS    read-write
     STATUS        current
     DESCRIPTION
	     "Setting this object administratively enables/disables TACACS authorization on the device."
     DEFVAL { disabled }
     ::= { wwpLeosTacacsClient 10 }

 wwpLeosTacacsAccountingAdminState OBJECT-TYPE     
     SYNTAX        INTEGER {
			disabled(1),
			enabled(2)
                   }
     MAX-ACCESS    read-write
     STATUS        current
     DESCRIPTION
	     "Setting this object administratively enables/disables TACACS accounting on the device."
     DEFVAL { disabled }
     ::= { wwpLeosTacacsClient 11 }

 wwpLeosTacacsSyslogAdminState OBJECT-TYPE     
     SYNTAX        INTEGER {
			disabled(1),
			enabled(2)
                   }
     MAX-ACCESS    read-write
     STATUS        current
     DESCRIPTION
	     "Setting this object administratively enables/disables TACACS Syslog messages on the device."
     DEFVAL { disabled }
     ::= { wwpLeosTacacsClient 12 }


 wwpLeosTacacsClientServerTable OBJECT-TYPE
     SYNTAX         SEQUENCE OF WwpLeosTacacsClientServerEntry
     MAX-ACCESS     not-accessible
     STATUS         current
     DESCRIPTION
	     "Lists the possible TACACS servers.
	      While creating an entry, the following objects must be specified:
	      wwpLeosTacacsClientServerStatus, wwpLeosTacacsClientServerAddr.
	      SNMP multiple set operation must be used to create the entry."
     ::= { wwpLeosTacacsClient 13 }

 wwpLeosTacacsClientServerEntry OBJECT-TYPE
     SYNTAX       WwpLeosTacacsClientServerEntry
     MAX-ACCESS   not-accessible
     STATUS       current
     DESCRIPTION
	     "TACACS server entry."
     INDEX { wwpLeosTacacsClientServerIndex}
     ::= { wwpLeosTacacsClientServerTable 1 }
		
 WwpLeosTacacsClientServerEntry ::= SEQUENCE {
     wwpLeosTacacsClientServerIndex			      Integer32,     
     wwpLeosTacacsClientServerAddr                            DisplayString,     
     wwpLeosTacacsClientServerResolvedAddr                    IpAddress,
     wwpLeosTacacsClientServerPriority			      Integer32,
     wwpLeosTacacsClientServerAuthPort                        Integer32,     
     wwpLeosTacacsClientServerAccessRequests                  Counter32,
     wwpLeosTacacsClientServerAccessRetransmissions           Counter32,
     wwpLeosTacacsClientServerAccessAccepts                   Counter32,
     wwpLeosTacacsClientServerAccessRejects                   Counter32,
     wwpLeosTacacsClientServerMalformedAccessResponses        Counter32,
     wwpLeosTacacsClientServerBadAuthenticators               Counter32,
     wwpLeosTacacsClientServerPendingRequests                 Gauge32,
     wwpLeosTacacsClientServerTimeouts                        Counter32,
     wwpLeosTacacsClientServerUnknownTypes                    Counter32,
     wwpLeosTacacsClientServerBadHeaderSequence               Counter32,    
     wwpLeosTacacsClientServerStatus                          RowStatus,     
     wwpLeosTacacsClientServerApplication                     INTEGER,
     wwpLeosTacacsClientServerClearStatistics                 TruthValue,
     wwpLeosTacacsClientGlobalAuthorizationAccessRequests                  Counter32,
     wwpLeosTacacsClientGlobalAuthorizationAccessRetransmissions           Counter32,
     wwpLeosTacacsClientGlobalAuthorizationAccessAccepts                   Counter32,
     wwpLeosTacacsClientGlobalAuthorizationAccessRejects                   Counter32,
     wwpLeosTacacsClientGlobalAuthorizationMalformedAccessResponses        Counter32,
     wwpLeosTacacsClientGlobalAuthorizationBadAuthenticators               Counter32,
     wwpLeosTacacsClientGlobalAuthorizationTimeouts                        Counter32,
     wwpLeosTacacsClientGlobalAuthorizationUnknownTypes                    Counter32,  
     wwpLeosTacacsClientGlobalAuthorizationBadHeaderSequence               Counter32,  
     
     wwpLeosTacacsClientGlobalAccountingAccessRequests                  Counter32,
     wwpLeosTacacsClientGlobalAccountingAccessRetransmissions           Counter32,
     wwpLeosTacacsClientGlobalAccountingAccessAccepts                   Counter32,
     wwpLeosTacacsClientGlobalAccountingAccessRejects                   Counter32,
     wwpLeosTacacsClientGlobalAccountingMalformedAccessResponses        Counter32,
     wwpLeosTacacsClientGlobalAccountingBadAuthenticators               Counter32,
     wwpLeosTacacsClientGlobalAccountingTimeouts                        Counter32,
     wwpLeosTacacsClientGlobalAccountingUnknownTypes                    Counter32,  
     wwpLeosTacacsClientGlobalAccountingBadHeaderSequence               Counter32,
     wwpLeosTacacsClientServerResolvedInetAddrType                      InetAddressType,
     wwpLeosTacacsClientServerResolvedInetAddr                          InetAddress
 }

 wwpLeosTacacsClientServerIndex OBJECT-TYPE
     SYNTAX       Integer32 (1..8)
     MAX-ACCESS   not-accessible
     STATUS       current
     DESCRIPTION
	     "Specifies the index of this table."
     ::= { wwpLeosTacacsClientServerEntry 1 }
	
 wwpLeosTacacsClientServerAddr OBJECT-TYPE
     SYNTAX       DisplayString (SIZE (0..64))
     MAX-ACCESS   read-write
     STATUS       current
     DESCRIPTION
	     "Host name or IP address of the TACACS server."
     ::= { wwpLeosTacacsClientServerEntry 2 }

 wwpLeosTacacsClientServerResolvedAddr OBJECT-TYPE
     SYNTAX       IpAddress
     MAX-ACCESS   read-only
     STATUS       current
     DESCRIPTION
   	     "When wwpLeosTacacsClientServerAddr represents:
          Host name    : The resolved address is either the Ipv4 address or Ipv6 address.
          Ipv4 address : The resolved address is the same Ipv4 address.
          Ipv6 address : The resolved address is the same Ipv6 address.
              
          When the resolved address represents:
          Ipv4 address : wwpLeosTacacsClientServerResolvedAddr represents the resolved Ipv4 address.
          wwpLeosTacacsClientServerResolvedInetAddr used in conjunction with wwpLeosTacacsClientServerResolvedInetAddrType
          represents the same Ipv4 address.
          Ipv6 address : wwpLeosTacacsClientServerResolvedAddr represents 0.0.0.0.
          wwpLeosTacacsClientServerResolvedInetAddr used in conjunction with wwpLeosTacacsClientServerResolvedInetAddrType
          represents the Ipv6 address."
     ::= { wwpLeosTacacsClientServerEntry 3 }
 
  wwpLeosTacacsClientServerPriority OBJECT-TYPE
     SYNTAX       Integer32
     MAX-ACCESS   read-write
     STATUS       current
     DESCRIPTION
	     "Specifies the priority of TACACS servers configured on the device. 
	     This is the order in which the servers are accessed."
     ::= { wwpLeosTacacsClientServerEntry 4 } 

 wwpLeosTacacsClientServerAuthPort OBJECT-TYPE
      SYNTAX      Integer32 (0..65535)
      MAX-ACCESS  read-write
      STATUS      current
      DESCRIPTION
	      "The destination TCP port number to which TACACS
	      messages should be sent.  The TACACS server is not
	      used for authentication if this port number is 0."
      DEFVAL { 49 }
      ::= { wwpLeosTacacsClientServerEntry 5 }

-- Request/Response statistics
--
-- TotalIncomingPackets = Accepts + Rejects + UnknownTypes
--
-- TotalIncomingPackets - MalformedResponses - BadAuthenticators -
-- UnknownTypes - PacketsDropped = Successfully received
--
-- AccessRequests + PendingRequests + ClientTimeouts =
-- Successfully Received
--
--

 wwpLeosTacacsClientServerAccessRequests OBJECT-TYPE
      SYNTAX Counter32
      MAX-ACCESS read-only
      STATUS current
      DESCRIPTION
            "The number of TACACS Access-Request packets sent
             to this server from the global TACACS client. This does not include retransmissions."
      ::= { wwpLeosTacacsClientServerEntry 6 }

 wwpLeosTacacsClientServerAccessRetransmissions OBJECT-TYPE
      SYNTAX Counter32
      MAX-ACCESS read-only
      STATUS current
      DESCRIPTION
            "The number of TACACS Access-Retransmission packets
             retransmitted to this TACACS authentication server from the global TACACS client."
      ::= { wwpLeosTacacsClientServerEntry 7 }

 wwpLeosTacacsClientServerAccessAccepts OBJECT-TYPE
      SYNTAX Counter32
      MAX-ACCESS read-only
      STATUS current
      DESCRIPTION
            "The number of TACACS Access-Accept packets
             (valid or invalid) received from this server by the global TACACS client."
      ::= { wwpLeosTacacsClientServerEntry 8 }

 wwpLeosTacacsClientServerAccessRejects OBJECT-TYPE
      SYNTAX Counter32
      MAX-ACCESS read-only
      STATUS current
      DESCRIPTION
            "The number of TACACS Access-Reject packets
             (valid or invalid) received from this server by the global TACACS client."
      ::= { wwpLeosTacacsClientServerEntry  9 }

 -- "Access-Response" includes an Access-Accept, Access-Challenge
 -- or Access-Reject

 wwpLeosTacacsClientServerMalformedAccessResponses OBJECT-TYPE
      SYNTAX Counter32
      MAX-ACCESS read-only
      STATUS current
      DESCRIPTION
            "The number of malformed TACACS Access-Response
             packets received from this server by the global TACACS client.
             Malformed packets include packets with
             an invalid length. Bad authenticators or
             Signature attributes or unknown types are not
             included as malformed access responses."
      ::= { wwpLeosTacacsClientServerEntry 10 }

 wwpLeosTacacsClientServerBadAuthenticators OBJECT-TYPE
      SYNTAX Counter32
      MAX-ACCESS read-only
      STATUS current
      DESCRIPTION
            "The number of TACACS Access-BadAuthenticator packets
             containing invalid authenticators or Signature
             attributes received from this server by the global TACACS client."
      ::= { wwpLeosTacacsClientServerEntry 11 }

 wwpLeosTacacsClientServerPendingRequests OBJECT-TYPE
      SYNTAX Gauge32
      MAX-ACCESS read-only
      STATUS deprecated
      DESCRIPTION
            "The number of TACACS Access-PendingRequest packets
             destined for this server from the global TACACS client that have not yet timed out
             or received a response. This variable is incremented
             when an Access-Request is sent and decremented due to
             receipt of an Access-Accept, Access-Reject or
             Access-Challenge, a timeout or retransmission."
      ::= { wwpLeosTacacsClientServerEntry 12 }

 wwpLeosTacacsClientServerTimeouts OBJECT-TYPE
     SYNTAX Counter32
     MAX-ACCESS read-only
     STATUS current
     DESCRIPTION
            "The number of authentication timeouts to this server on behalf of the global TACACS client.
             After a timeout the client may retry to the same
             server, send to a different server, or
             give up. A retry to the same server is counted as a
             retransmit as well as a timeout. A send to a different
             server is counted as a Request as well as a timeout."
      ::= { wwpLeosTacacsClientServerEntry  13 }

 wwpLeosTacacsClientServerUnknownTypes OBJECT-TYPE
      SYNTAX Counter32
      MAX-ACCESS read-only
      STATUS current
      DESCRIPTION
            "The number of TACACS packets of unknown type that
             were received from this server on the authentication port by the global TACACS client."
      ::= { wwpLeosTacacsClientServerEntry  14 }

 wwpLeosTacacsClientServerBadHeaderSequence OBJECT-TYPE
      SYNTAX Counter32
      MAX-ACCESS read-only
      STATUS current
      DESCRIPTION
            "The number of TACACS packets of that were
             received from this server on the authentication port by the global TACACS client
             and dropped for some other reason by the client."
      ::= { wwpLeosTacacsClientServerEntry  15}
		
 wwpLeosTacacsClientServerStatus OBJECT-TYPE
      SYNTAX        RowStatus
      MAX-ACCESS    read-create
      STATUS        current
      DESCRIPTION
            "To create a row in this table, set this object to createAndGo(4).

            While creating an entry, the following objects must be specified:
	    wwpLeosTacacsClientServerStatus, wwpLeosTacacsClientServerAddr.
	    SNMP multiple set operation must be used to create the entry.

            To disable a TACACS server, set wwpLeosTacacsClientServerStatus
	    object to 'notInService'."
      ::= { wwpLeosTacacsClientServerEntry 16 } 

 wwpLeosTacacsClientServerApplication OBJECT-TYPE
      SYNTAX 		INTEGER {
      					userLogin(1),
					dot1x(2),
      					all(3)   
				}
      MAX-ACCESS 	read-create
      STATUS 		deprecated
      DESCRIPTION
            "This object specifies how the TACACS server should be used for authentication.
             Whether this TACACS server should be used for userLogin authentication or dot1x authentication
             or both is decided by the value of this object. Dot1x is not supported on all platforms."
      DEFVAL 	{userLogin}
      ::= { wwpLeosTacacsClientServerEntry  17}
 wwpLeosTacacsClientServerClearStatistics OBJECT-TYPE
      SYNTAX            TruthValue
      MAX-ACCESS        read-write
      STATUS            current
      DESCRIPTION
            "This object clears the statistics for a server."
      DEFVAL { false }
      ::= { wwpLeosTacacsClientServerEntry  18}

 --  ADDED EXTRA TWAMP STATS for Authorization------------------
 
  wwpLeosTacacsClientGlobalAuthorizationAccessRequests OBJECT-TYPE
       SYNTAX Counter32
       MAX-ACCESS read-only
       STATUS current
       DESCRIPTION
             "The number of TACACS Access-Request packets sent
              to this server. This does not include retransmissions."
       ::= { wwpLeosTacacsClientServerEntry 19 }
 
  wwpLeosTacacsClientGlobalAuthorizationAccessRetransmissions OBJECT-TYPE
       SYNTAX Counter32
       MAX-ACCESS read-only
       STATUS current
       DESCRIPTION
             "The number of TACACS Access-Request packets
              retransmitted to this TACACS authentication server."
       ::= { wwpLeosTacacsClientServerEntry 20 }
 
  wwpLeosTacacsClientGlobalAuthorizationAccessAccepts OBJECT-TYPE
       SYNTAX Counter32
       MAX-ACCESS read-only
       STATUS current
       DESCRIPTION
             "The number of TACACS Access-Accept packets
              (valid or invalid) received from this server."
       ::= { wwpLeosTacacsClientServerEntry 21 }
 
  wwpLeosTacacsClientGlobalAuthorizationAccessRejects OBJECT-TYPE
       SYNTAX Counter32
       MAX-ACCESS read-only
       STATUS current
       DESCRIPTION
             "The number of TACACS Access-Reject packets
              (valid or invalid) received from this server."
       ::= { wwpLeosTacacsClientServerEntry  22 }
 
  -- "Access-Response" includes an Access-Accept, Access-Challenge
  -- or Access-Reject
 
  wwpLeosTacacsClientGlobalAuthorizationMalformedAccessResponses OBJECT-TYPE
       SYNTAX Counter32
       MAX-ACCESS read-only
       STATUS current
       DESCRIPTION
             "The number of malformed TACACS Access-Response
              packets received from this server.
              Malformed packets include packets with
              an invalid length. Bad authenticators or
              signature attributes or unknown types are not
              included as malformed access responses."
       ::= { wwpLeosTacacsClientServerEntry 23 }
 
  wwpLeosTacacsClientGlobalAuthorizationBadAuthenticators OBJECT-TYPE
       SYNTAX Counter32
       MAX-ACCESS read-only
       STATUS current
       DESCRIPTION
             "The number of TACACS Access-Response packets
              containing invalid authenticators or signature
              attributes received from this server."
       ::= { wwpLeosTacacsClientServerEntry 24 }
 
 
  wwpLeosTacacsClientGlobalAuthorizationTimeouts OBJECT-TYPE
      SYNTAX Counter32
      MAX-ACCESS read-only
      STATUS current
      DESCRIPTION
             "The number of authentication timeouts to this server.
              After a timeout the client may retry sending to the same
              server, send to a different server, or
              give up. A retry to the same server is counted as a
              retransmit as well as a timeout. A send to a different
              server is counted as a request as well as a timeout."
       ::= { wwpLeosTacacsClientServerEntry  25 }
 
  wwpLeosTacacsClientGlobalAuthorizationUnknownTypes OBJECT-TYPE
       SYNTAX Counter32
       MAX-ACCESS read-only
       STATUS current
       DESCRIPTION
             "The number of TACACS packets of unknown type that
              were received from this server on the authentication port."
       ::= { wwpLeosTacacsClientServerEntry  26 }
 
  wwpLeosTacacsClientGlobalAuthorizationBadHeaderSequence OBJECT-TYPE
       SYNTAX Counter32
       MAX-ACCESS read-only
       STATUS current
       DESCRIPTION
             "The number of TACACS packets that were
              received from this server on the authentication port
              and dropped for some other reason."
       ::= { wwpLeosTacacsClientServerEntry  27}
                     
      
 --  ADDED EXTRA TWAMP STATS for Accounting------------------
 
  wwpLeosTacacsClientGlobalAccountingAccessRequests OBJECT-TYPE
       SYNTAX Counter32
       MAX-ACCESS read-only
       STATUS current
       DESCRIPTION
             "The number of TACACS Access-Request packets sent
              to this server. This does not include retransmissions."
       ::= { wwpLeosTacacsClientServerEntry 28 }
 
  wwpLeosTacacsClientGlobalAccountingAccessRetransmissions OBJECT-TYPE
       SYNTAX Counter32
       MAX-ACCESS read-only
       STATUS current
       DESCRIPTION
             "The number of TACACS Access-Request packets
              retransmitted to this TACACS authentication server."
       ::= { wwpLeosTacacsClientServerEntry 29 }
 
  wwpLeosTacacsClientGlobalAccountingAccessAccepts OBJECT-TYPE
       SYNTAX Counter32
       MAX-ACCESS read-only
       STATUS current
       DESCRIPTION
             "The number of TACACS Access-Accept packets
              (valid or invalid) received from this server."
       ::= { wwpLeosTacacsClientServerEntry 30 }
 
  wwpLeosTacacsClientGlobalAccountingAccessRejects OBJECT-TYPE
       SYNTAX Counter32
       MAX-ACCESS read-only
       STATUS current
       DESCRIPTION
             "The number of TACACS Access-Reject packets
              (valid or invalid) received from this server."
       ::= { wwpLeosTacacsClientServerEntry 31 }
 
  -- "Access-Response" includes an Access-Accept, Access-Challenge
  -- or Access-Reject
 
  wwpLeosTacacsClientGlobalAccountingMalformedAccessResponses OBJECT-TYPE
       SYNTAX Counter32
       MAX-ACCESS read-only
       STATUS current
       DESCRIPTION
             "The number of malformed TACACS Access-Response
              packets received from this server.
              Malformed packets include packets with
              an invalid length. Bad authenticators or
              signature attributes or unknown types are not
              included as malformed access responses."
       ::= { wwpLeosTacacsClientServerEntry 32 }
 
  wwpLeosTacacsClientGlobalAccountingBadAuthenticators OBJECT-TYPE
       SYNTAX Counter32
       MAX-ACCESS read-only
       STATUS current
       DESCRIPTION
             "The number of TACACS Access-Response packets
              containing invalid authenticators or signature
              attributes received from this server."
       ::= { wwpLeosTacacsClientServerEntry 33 }
 
 
  wwpLeosTacacsClientGlobalAccountingTimeouts OBJECT-TYPE
      SYNTAX Counter32
      MAX-ACCESS read-only
      STATUS current
      DESCRIPTION
             "The number of authentication timeouts to this server.
              After a timeout the client may retry sending to the same
              server, send to a different server, or
              give up. A retry to the same server is counted as a
              retransmit as well as a timeout. A send to a different
              server is counted as a request as well as a timeout."
       ::= { wwpLeosTacacsClientServerEntry  34 }
 
  wwpLeosTacacsClientGlobalAccountingUnknownTypes OBJECT-TYPE
       SYNTAX Counter32
       MAX-ACCESS read-only
       STATUS current
       DESCRIPTION
             "The number of TACACS packets of unknown type that
              were received from this server on the authentication port."
       ::= { wwpLeosTacacsClientServerEntry  35 }
 
  wwpLeosTacacsClientGlobalAccountingBadHeaderSequence OBJECT-TYPE
       SYNTAX Counter32
       MAX-ACCESS read-only
       STATUS current
       DESCRIPTION
             "The number of TACACS packets that were
              received from this server on the authentication port
              and dropped for some other reason."
       ::= { wwpLeosTacacsClientServerEntry  36}

  wwpLeosTacacsClientServerResolvedInetAddrType OBJECT-TYPE
       SYNTAX       InetAddressType
       MAX-ACCESS   read-only
       STATUS       current
       DESCRIPTION
	     "Specifies the resolved IP address type .	Used in conjunction with 
              wwpLeosTacacsClientServerResolvedInetAddr.
              When set to :
              ipv4 : wwpLeosTacacsClientServerResolvedInetAddr should be compliant 
                     with InetAddressIPv4 
              ipv6 : wwpLeosTacacsClientServerResolvedInetAddr should be compliant 
                     with InetAddressIPv6 "
     ::= { wwpLeosTacacsClientServerEntry 37 }
 
  wwpLeosTacacsClientServerResolvedInetAddr OBJECT-TYPE
       SYNTAX       InetAddress
       MAX-ACCESS   read-only
       STATUS       current
       DESCRIPTION
	     "Specifies the resolved IP address if wwpLeosTacacsClientServerAddr
              is set to host name.  If wwpLeosTacacsClientServerAddr is set to IP
              address then wwpLeosTacacsClientServerResolvedInetAddress contains the
              same information as wwpLeosTacacsClientServerAddr.  This OID is
              used in conjuction with wwpLeosTacacsClientServerResolvedInetAddrType."
     ::= { wwpLeosTacacsClientServerEntry 38 }
                
   
   --  END OF TWAMP STATS-----------------
 
 wwpLeosTacacsClientAuthenticationServerTable OBJECT-TYPE
     SYNTAX         SEQUENCE OF WwpLeosTacacsClientAuthenticationServerEntry
     MAX-ACCESS     not-accessible
     STATUS         current
     DESCRIPTION
             "Lists the possible TACACS servers.
              While creating an entry, following objects must be specified:
              wwpLeosTacacsClientAuthenticationServerStatus, wwpLeosTacacsClientAuthenticationServerAddr.
              SNMP multiple set operation must be used to create the entry."
     ::= { wwpLeosTacacsClient 14 }

 wwpLeosTacacsClientAuthenticationServerEntry OBJECT-TYPE
     SYNTAX       WwpLeosTacacsClientAuthenticationServerEntry
     MAX-ACCESS   not-accessible
     STATUS       current
     DESCRIPTION
             "TACACS server entry."
     INDEX { wwpLeosTacacsClientAuthenticationServerIndex}
     ::= { wwpLeosTacacsClientAuthenticationServerTable 1 }
                
 WwpLeosTacacsClientAuthenticationServerEntry ::= SEQUENCE {
     wwpLeosTacacsClientAuthenticationServerIndex                               Integer32,     
     wwpLeosTacacsClientAuthenticationServerAddr                            DisplayString,     
     wwpLeosTacacsClientAuthenticationServerResolvedAddr                    IpAddress,
     wwpLeosTacacsClientAuthenticationServerPriority                    Integer32,
     wwpLeosTacacsClientAuthenticationServerAuthPort                        Integer32,     
     wwpLeosTacacsClientAuthenticationServerAccessRequests                  Counter32,
     wwpLeosTacacsClientAuthenticationServerAccessRetransmissions           Counter32,
     wwpLeosTacacsClientAuthenticationServerAccessAccepts                   Counter32,
     wwpLeosTacacsClientAuthenticationServerAccessRejects                   Counter32,
     wwpLeosTacacsClientAuthenticationServerMalformedAccessResponses        Counter32,
     wwpLeosTacacsClientAuthenticationServerBadAuthenticators               Counter32,
     wwpLeosTacacsClientAuthenticationServerPendingRequests                 Gauge32,
     wwpLeosTacacsClientAuthenticationServerTimeouts                        Counter32,
     wwpLeosTacacsClientAuthenticationServerUnknownTypes                    Counter32,
     wwpLeosTacacsClientAuthenticationServerBadHeaderSequence               Counter32,    
     wwpLeosTacacsClientAuthenticationServerStatus                          RowStatus,     
     wwpLeosTacacsClientAuthenticationServerApplication                     INTEGER,
     wwpLeosTacacsClientAuthenticationServerClearStatistics                 TruthValue,
     wwpLeosTacacsClientAuthenticationServerResolvedInetAddrType            InetAddressType,
     wwpLeosTacacsClientAuthenticationServerResolvedInetAddr                InetAddress
 }

 wwpLeosTacacsClientAuthenticationServerIndex OBJECT-TYPE
     SYNTAX       Integer32 (1..8)
     MAX-ACCESS   not-accessible
     STATUS       current
     DESCRIPTION
             "Specifies the index of this table."
     ::= { wwpLeosTacacsClientAuthenticationServerEntry 1 }
        
 wwpLeosTacacsClientAuthenticationServerAddr OBJECT-TYPE
     SYNTAX       DisplayString (SIZE (0..64))
     MAX-ACCESS   read-write
     STATUS       current
     DESCRIPTION
             "Host name or IP address of the TACACS server."
     ::= { wwpLeosTacacsClientAuthenticationServerEntry 2 }

 wwpLeosTacacsClientAuthenticationServerResolvedAddr OBJECT-TYPE
     SYNTAX       IpAddress
     MAX-ACCESS   read-only
     STATUS       current
     DESCRIPTION
	     "When wwpLeosTacacsClientAuthenticationServerAddr represents:
          Host name    : The resolved address is either the Ipv4 address or Ipv6 address. 
          Ipv4 address : The resolved address is the same Ipv4 address.
          Ipv6 address : The resolved address is the same Ipv6 address.
              
          When the resolved address represents:
          Ipv4 address : wwpLeosTacacsClientAuthenticationServerResolvedAddr represents the resolved Ipv4 address.
          wwpLeosTacacsClientAuthenticationServerResolvedInetAddr used in conjunction with
          wwpLeosTacacsClientAuthenticationServerResolvedInetAddrType represents the same Ipv4 address.
          Ipv6 address : wwpLeosTacacsClientAuthenticationServerResolvedAddr represents 0.0.0.0.
          wwpLeosTacacsClientAuthenticationServerResolvedInetAddr used in conjunction with
          wwpLeosTacacsClientAuthenticationServerResolvedInetAddrType represents the Ipv6 address."
     ::= { wwpLeosTacacsClientAuthenticationServerEntry 3 }
 
  wwpLeosTacacsClientAuthenticationServerPriority OBJECT-TYPE
     SYNTAX       Integer32
     MAX-ACCESS   read-write
     STATUS       current
     DESCRIPTION
             "Specifies the priority of TACACS servers configured on the device. 
             This is the order in which the servers are accessed."
     ::= { wwpLeosTacacsClientAuthenticationServerEntry 4 } 

 wwpLeosTacacsClientAuthenticationServerAuthPort OBJECT-TYPE
      SYNTAX      Integer32 (0..65535)
      MAX-ACCESS  read-write
      STATUS      current
      DESCRIPTION
              "The destination TCP port number to which TACACS
              messages should be sent.  The TACACS server is not
              used for authentication if this port number is 0."
      DEFVAL { 49 }
      ::= { wwpLeosTacacsClientAuthenticationServerEntry 5 }

-- Request/Response statistics
--
-- TotalIncomingPackets = Accepts + Rejects + UnknownTypes
--
-- TotalIncomingPackets - MalformedResponses - BadAuthenticators -
-- UnknownTypes - PacketsDropped = Successfully received
--
-- AccessRequests + PendingRequests + ClientTimeouts =
-- Successfully Received
--
--

 wwpLeosTacacsClientAuthenticationServerAccessRequests OBJECT-TYPE
      SYNTAX Counter32
      MAX-ACCESS read-only
      STATUS current
      DESCRIPTION
            "The number of TACACS Access-Request packets sent
             to this server. This does not include retransmissions."
      ::= { wwpLeosTacacsClientAuthenticationServerEntry 6 }

 wwpLeosTacacsClientAuthenticationServerAccessRetransmissions OBJECT-TYPE
      SYNTAX Counter32
      MAX-ACCESS read-only
      STATUS current
      DESCRIPTION
            "The number of TACACS Access-Request packets
             retransmitted to this TACACS authentication server."
      ::= { wwpLeosTacacsClientAuthenticationServerEntry 7 }

 wwpLeosTacacsClientAuthenticationServerAccessAccepts OBJECT-TYPE
      SYNTAX Counter32
      MAX-ACCESS read-only
      STATUS current
      DESCRIPTION
            "The number of TACACS Access-Accept packets
             (valid or invalid) received from this server."
      ::= { wwpLeosTacacsClientAuthenticationServerEntry 8 }

 wwpLeosTacacsClientAuthenticationServerAccessRejects OBJECT-TYPE
      SYNTAX Counter32
      MAX-ACCESS read-only
      STATUS current
      DESCRIPTION
            "The number of TACACS Access-Reject packets
             (valid or invalid) received from this server."
      ::= { wwpLeosTacacsClientAuthenticationServerEntry  9 }

 -- "Access-Response" includes an Access-Accept, Access-Challenge
 -- or Access-Reject

 wwpLeosTacacsClientAuthenticationServerMalformedAccessResponses OBJECT-TYPE
      SYNTAX Counter32
      MAX-ACCESS read-only
      STATUS current
      DESCRIPTION
            "The number of malformed TACACS Access-Response
             packets received from this server.
             Malformed packets include packets with
             an invalid length. Bad authenticators or
             Signature attributes or unknown types are not
             included as malformed access responses."
      ::= { wwpLeosTacacsClientAuthenticationServerEntry 10 }

 wwpLeosTacacsClientAuthenticationServerBadAuthenticators OBJECT-TYPE
      SYNTAX Counter32
      MAX-ACCESS read-only
      STATUS current
      DESCRIPTION
            "The number of TACACS Access-Response packets
             containing invalid authenticators or Signature
             attributes received from this server."
      ::= { wwpLeosTacacsClientAuthenticationServerEntry 11 }

 wwpLeosTacacsClientAuthenticationServerPendingRequests OBJECT-TYPE
      SYNTAX Gauge32
      MAX-ACCESS read-only
      STATUS deprecated
      DESCRIPTION
            "The number of TACACS Access-Request packets
             destined for this server that have not yet timed out
             or received a response. This variable is incremented
             when an Access-Request is sent and decremented due to
             receipt of an Access-Accept, Access-Reject or
             Access-Challenge, a timeout or retransmission."
      ::= { wwpLeosTacacsClientAuthenticationServerEntry 12 }

 wwpLeosTacacsClientAuthenticationServerTimeouts OBJECT-TYPE
     SYNTAX Counter32
     MAX-ACCESS read-only
     STATUS current
     DESCRIPTION
            "The number of authentication timeouts to this server.
             After a timeout the client may retry to the same
             server, send to a different server, or
             give up. A retry to the same server is counted as a
             retransmit as well as a timeout. A send to a different
             server is counted as a Request as well as a timeout."
      ::= { wwpLeosTacacsClientAuthenticationServerEntry  13 }

 wwpLeosTacacsClientAuthenticationServerUnknownTypes OBJECT-TYPE
      SYNTAX Counter32
      MAX-ACCESS read-only
      STATUS current
      DESCRIPTION
            "The number of TACACS packets of unknown type that
             were received from this server on the authentication port."
      ::= { wwpLeosTacacsClientAuthenticationServerEntry  14 }

 wwpLeosTacacsClientAuthenticationServerBadHeaderSequence OBJECT-TYPE
      SYNTAX Counter32
      MAX-ACCESS read-only
      STATUS current
      DESCRIPTION
            "The number of TACACS packets that were
             received from this server on the authentication port
             and dropped for some other reason."
      ::= { wwpLeosTacacsClientAuthenticationServerEntry  15}
                
 wwpLeosTacacsClientAuthenticationServerStatus OBJECT-TYPE
      SYNTAX        RowStatus
      MAX-ACCESS    read-create
      STATUS        current
      DESCRIPTION
            "To create a row in this table, set this object to createAndGo(4).

            While creating an entry, the following objects must be specified:
            wwpLeosTacacsClientAuthenticationServerStatus, wwpLeosTacacsClientAuthenticationServerAddr.
            SNMP multiple set operation must be used to create the entry.

            To disable a TACACS server, set wwpLeosTacacsClientAuthenticationServerStatus
            object to 'notInService'."
      ::= { wwpLeosTacacsClientAuthenticationServerEntry 16 } 

 wwpLeosTacacsClientAuthenticationServerApplication OBJECT-TYPE
      SYNTAX            INTEGER {
                                        userLogin(1),
                                        dot1x(2),
                                        all(3)   
                                }
      MAX-ACCESS        read-create
      STATUS            deprecated
      DESCRIPTION
            "This object specifies how the TACACS server should be used for authentication.
             Whether this TACACS server should be used for userLogin authentication or dot1x authentication 
             or both is decided by the value of this object. Dot1x is not supported on all platforms."
      DEFVAL    {userLogin}
      ::= { wwpLeosTacacsClientAuthenticationServerEntry  17}

 wwpLeosTacacsClientAuthenticationServerClearStatistics OBJECT-TYPE
      SYNTAX            TruthValue
      MAX-ACCESS        read-write
      STATUS            current
      DESCRIPTION
            "This object clears the statistics for a server."
      DEFVAL { false }
      ::= { wwpLeosTacacsClientAuthenticationServerEntry  18}


 wwpLeosTacacsClientAuthenticationServerResolvedInetAddrType OBJECT-TYPE
      SYNTAX       InetAddressType
      MAX-ACCESS   read-only
      STATUS       current
      DESCRIPTION
	    "Specifies the resolved IP address type.  Used in conjunction with
             wwpLeosTacacsClientAuthenticationServerResolvedInetAddr.
             When set to :
             ipv4 : wwpLeosTacacsClientAuthenticationServerResolvedInetAddr should
                    be compliant with InetAddressIPv4
             ipv6 : wwpLeosTacacsClientAuthenticationServerResolvedInetAddr should
                    be compliant with InetAddressIPv6 "
     ::= { wwpLeosTacacsClientAuthenticationServerEntry 19 }
 
 wwpLeosTacacsClientAuthenticationServerResolvedInetAddr OBJECT-TYPE
      SYNTAX       InetAddress
      MAX-ACCESS   read-only
      STATUS       current
      DESCRIPTION
            "Specifies the resolved IP address if wwpLeosTacacsClientAuthenticationServerAddr
             is set to host name.  If wwpLeosTacacsClientAuthenticationServerAddr is set to IP
             address then wwpLeosTacacsClientAuthenticationServerResolvedInetAddr
             contains the same information as wwpLeosTacacsClientAuthenticationServerAddr.
             This OID should be used in conjuction with 
             wwpLeosTacacsClientAuthenticationServerResolvedInetAddrType."
     ::= { wwpLeosTacacsClientAuthenticationServerEntry 20}

 
 --
 --wwpLeosTacacsClientAuthorizationServerTable
 --
 wwpLeosTacacsClientAuthorizationServerTable OBJECT-TYPE
     SYNTAX         SEQUENCE OF WwpLeosTacacsClientAuthorizationServerEntry
     MAX-ACCESS     not-accessible
     STATUS         current
     DESCRIPTION
             "Lists the possible TACACS servers.
              While creating an entry, the following objects must be specified:
              wwpLeosTacacsClientAuthorizationServerStatus, wwpLeosTacacsClientAuthorizationServerAddr.
              SNMP multiple set operation must be used to create the entry."
     ::= { wwpLeosTacacsClient 15 }

 wwpLeosTacacsClientAuthorizationServerEntry OBJECT-TYPE
     SYNTAX       WwpLeosTacacsClientAuthorizationServerEntry
     MAX-ACCESS   not-accessible
     STATUS       current
     DESCRIPTION
             "TACACS server entry."
     INDEX { wwpLeosTacacsClientAuthorizationServerIndex}
     ::= { wwpLeosTacacsClientAuthorizationServerTable 1 }
                
 WwpLeosTacacsClientAuthorizationServerEntry ::= SEQUENCE {
     wwpLeosTacacsClientAuthorizationServerIndex                               Integer32,     
     wwpLeosTacacsClientAuthorizationServerAddr                            DisplayString,     
     wwpLeosTacacsClientAuthorizationServerResolvedAddr                    IpAddress,
     wwpLeosTacacsClientAuthorizationServerPriority                            Integer32,
     wwpLeosTacacsClientAuthorizationServerAuthPort                        Integer32,     
     wwpLeosTacacsClientAuthorizationServerAccessRequests                  Counter32,
     wwpLeosTacacsClientAuthorizationServerAccessRetransmissions           Counter32,
     wwpLeosTacacsClientAuthorizationServerAccessAccepts                   Counter32,
     wwpLeosTacacsClientAuthorizationServerAccessRejects                   Counter32,
     wwpLeosTacacsClientAuthorizationServerMalformedAccessResponses        Counter32,
     wwpLeosTacacsClientAuthorizationServerBadAuthenticators               Counter32,
     wwpLeosTacacsClientAuthorizationServerPendingRequests                 Gauge32,
     wwpLeosTacacsClientAuthorizationServerTimeouts                        Counter32,
     wwpLeosTacacsClientAuthorizationServerUnknownTypes                    Counter32,
     wwpLeosTacacsClientAuthorizationServerBadHeaderSequence               Counter32,    
     wwpLeosTacacsClientAuthorizationServerStatus                          RowStatus,     
     wwpLeosTacacsClientAuthorizationServerApplication                 INTEGER,
     wwpLeosTacacsClientAuthorizationServerClearStatistics                 TruthValue,
     wwpLeosTacacsClientAuthorizationServerResolvedInetAddrType            InetAddressType,
     wwpLeosTacacsClientAuthorizationServerResolvedInetAddr                InetAddress
 }

 wwpLeosTacacsClientAuthorizationServerIndex OBJECT-TYPE
     SYNTAX       Integer32 (1..8)
     MAX-ACCESS   not-accessible
     STATUS       current
     DESCRIPTION
             "Specifies the index of this table."
     ::= { wwpLeosTacacsClientAuthorizationServerEntry 1 }
        
 wwpLeosTacacsClientAuthorizationServerAddr OBJECT-TYPE
     SYNTAX       DisplayString (SIZE (0..64))
     MAX-ACCESS   read-write
     STATUS       current
     DESCRIPTION
             "Host name or IP address of the TACACS server."
     ::= { wwpLeosTacacsClientAuthorizationServerEntry 2 }

 wwpLeosTacacsClientAuthorizationServerResolvedAddr OBJECT-TYPE
     SYNTAX       IpAddress
     MAX-ACCESS   read-only
     STATUS       current
     DESCRIPTION
	     "When wwpLeosTacacsClientAuthorizationServerAddr represents:
          Host name    : The resolved address is either the Ipv4 address or Ipv6 address.
          Ipv4 address : The resolved address is the same Ipv4 address.
          Ipv6 address : The resolved address is the same Ipv6 address.
              
          When the resolved address represents:
          Ipv4 address : wwpLeosTacacsClientAuthorizationServerResolvedAddr represents the resolved Ipv4 address.
          wwpLeosTacacsClientAuthorizationServerResolvedInetAddr used in conjunction with
          wwpLeosTacacsClientAuthorizationServerResolvedInetAddrType represents the same Ipv4 address.
          Ipv6 address : wwpLeosTacacsClientAuthorizationServerResolvedAddr represents 0.0.0.0.
          wwpLeosTacacsClientAuthorizationServerResolvedInetAddr used in conjunction with
          wwpLeosTacacsClientAuthorizationServerResolvedInetAddrType epresents the Ipv6 address."
     ::= { wwpLeosTacacsClientAuthorizationServerEntry 3 }
 
  wwpLeosTacacsClientAuthorizationServerPriority OBJECT-TYPE
     SYNTAX       Integer32
     MAX-ACCESS   read-write
     STATUS       current
     DESCRIPTION
             "Specifies the priority of TACACS servers configured on the device.
             This is the order in which the servers are accessed."
     ::= { wwpLeosTacacsClientAuthorizationServerEntry 4 } 

 wwpLeosTacacsClientAuthorizationServerAuthPort OBJECT-TYPE
      SYNTAX      Integer32 (0..65535)
      MAX-ACCESS  read-write
      STATUS      current
      DESCRIPTION
              "The destination TCP port number to which TACACS
              messages should be sent.  The TACACS server is not
              used for authentication if this port number is 0."
      DEFVAL { 49 }
      ::= { wwpLeosTacacsClientAuthorizationServerEntry 5 }

-- Request/Response statistics
--
-- TotalIncomingPackets = Accepts + Rejects + UnknownTypes
--
-- TotalIncomingPackets - MalformedResponses - BadAuthenticators -
-- UnknownTypes - PacketsDropped = Successfully received
--
-- AccessRequests + PendingRequests + ClientTimeouts =
-- Successfully Received
--
--

 wwpLeosTacacsClientAuthorizationServerAccessRequests OBJECT-TYPE
      SYNTAX Counter32
      MAX-ACCESS read-only
      STATUS current
      DESCRIPTION
            "The number of TACACS Access-Request packets sent
             to this server. This does not include retransmissions."
      ::= { wwpLeosTacacsClientAuthorizationServerEntry 6 }

 wwpLeosTacacsClientAuthorizationServerAccessRetransmissions OBJECT-TYPE
      SYNTAX Counter32
      MAX-ACCESS read-only
      STATUS current
      DESCRIPTION
            "The number of TACACS Access-Request packets
             retransmitted to this TACACS authentication server."
      ::= { wwpLeosTacacsClientAuthorizationServerEntry 7 }

 wwpLeosTacacsClientAuthorizationServerAccessAccepts OBJECT-TYPE
      SYNTAX Counter32
      MAX-ACCESS read-only
      STATUS current
      DESCRIPTION
            "The number of TACACS Access-Accept packets
             (valid or invalid) received from this server."
      ::= { wwpLeosTacacsClientAuthorizationServerEntry 8 }

 wwpLeosTacacsClientAuthorizationServerAccessRejects OBJECT-TYPE
      SYNTAX Counter32
      MAX-ACCESS read-only
      STATUS current
      DESCRIPTION
            "The number of TACACS Access-Reject packets
             (valid or invalid) received from this server."
      ::= { wwpLeosTacacsClientAuthorizationServerEntry  9 }

 -- "Access-Response" includes an Access-Accept, Access-Challenge
 -- or Access-Reject

 wwpLeosTacacsClientAuthorizationServerMalformedAccessResponses OBJECT-TYPE
      SYNTAX Counter32
      MAX-ACCESS read-only
      STATUS current
      DESCRIPTION
            "The number of malformed TACACS Access-Response
             packets received from this server.
             Malformed packets include packets with
             an invalid length. Bad authenticators or
             Signature attributes or unknown types are not
             included as malformed access responses."
      ::= { wwpLeosTacacsClientAuthorizationServerEntry 10 }

 wwpLeosTacacsClientAuthorizationServerBadAuthenticators OBJECT-TYPE
      SYNTAX Counter32
      MAX-ACCESS read-only
      STATUS current
      DESCRIPTION
            "The number of TACACS Access-Response packets
             containing invalid authenticators or Signature
             attributes received from this server."
      ::= { wwpLeosTacacsClientAuthorizationServerEntry 11 }

 wwpLeosTacacsClientAuthorizationServerPendingRequests OBJECT-TYPE
      SYNTAX Gauge32
      MAX-ACCESS read-only
      STATUS deprecated
      DESCRIPTION
            "The number of TACACS Access-Request packets
             destined for this server that have not yet timed out
             or received a response. This variable is incremented
             when an Access-Request is sent and decremented due to
             receipt of an Access-Accept, Access-Reject or
             Access-Challenge, a timeout or retransmission."
      ::= { wwpLeosTacacsClientAuthorizationServerEntry 12 }

 wwpLeosTacacsClientAuthorizationServerTimeouts OBJECT-TYPE
     SYNTAX Counter32
     MAX-ACCESS read-only
     STATUS current
     DESCRIPTION
            "The number of authentication timeouts to this server.
             After a timeout the client may retry to the same
             server, send to a different server, or
             give up. A retry to the same server is counted as a
             retransmit as well as a timeout. A send to a different
             server is counted as a Request as well as a timeout."
      ::= { wwpLeosTacacsClientAuthorizationServerEntry  13 }

 wwpLeosTacacsClientAuthorizationServerUnknownTypes OBJECT-TYPE
      SYNTAX Counter32
      MAX-ACCESS read-only
      STATUS current
      DESCRIPTION
            "The number of TACACS packets of unknown type that
             were received from this server on the authentication port."
      ::= { wwpLeosTacacsClientAuthorizationServerEntry  14 }

 wwpLeosTacacsClientAuthorizationServerBadHeaderSequence OBJECT-TYPE
      SYNTAX Counter32
      MAX-ACCESS read-only
      STATUS current
      DESCRIPTION
            "The number of TACACS packets that were
             received from this server on the authentication port
             and dropped for some other reason."
      ::= { wwpLeosTacacsClientAuthorizationServerEntry  15}
                
 wwpLeosTacacsClientAuthorizationServerStatus OBJECT-TYPE
      SYNTAX        RowStatus
      MAX-ACCESS    read-create
      STATUS        current
      DESCRIPTION
            "To create a row in this table, set this object to createAndGo(4).

            While creating an entry, the following objects must be specified:
            wwpLeosTacacsClientAuthorizationServerStatus, wwpLeosTacacsClientAuthorizationServerAddr.
            SNMP multiple set operation must be used to create the entry.

            To disable a TACACS server, set wwpLeosTacacsClientAuthorizationServerStatus
            object to 'notInService'."
      ::= { wwpLeosTacacsClientAuthorizationServerEntry 16 } 

 wwpLeosTacacsClientAuthorizationServerApplication OBJECT-TYPE
      SYNTAX            INTEGER {
                                        userLogin(1),
                                        dot1x(2),
                                        all(3)   
                                }
      MAX-ACCESS        read-create
      STATUS            deprecated
      DESCRIPTION
            "This object specifies how the TACACS server should be used for authentication.
             Whether this TACACS server should be used for userLogin authentication or dot1x authentication 
             or both is decided by the value of this object. Dot1x is not supported on all platforms."
      DEFVAL    {userLogin}
      ::= { wwpLeosTacacsClientAuthorizationServerEntry  17}

 wwpLeosTacacsClientAuthorizationServerClearStatistics OBJECT-TYPE
      SYNTAX            TruthValue
      MAX-ACCESS        read-write
      STATUS            current
      DESCRIPTION
            "This object clears the statistics for a server."
      DEFVAL { false }
      ::= { wwpLeosTacacsClientAuthorizationServerEntry  18} 

 wwpLeosTacacsClientAuthorizationServerResolvedInetAddrType OBJECT-TYPE
      SYNTAX       InetAddressType
      MAX-ACCESS   read-only
      STATUS       current
      DESCRIPTION
	    "Specifies the resolved IP address type.  Used in conjunction with 
             wwpLeosTacacsClientAuthorizationServerResolvedInetAddr.
             When set to :
             ipv4 : wwpLeosTacacsClientAuthorizationServerResolvedInetAddr should 
                    be compliant with InetAddressIPv4 
             ipv6 : wwpLeosTacacsClientAuthorizationServerResolvedInetAddr should 
                    be compliant with InetAddressIPv6."
     ::= { wwpLeosTacacsClientAuthorizationServerEntry 19 }
 
 wwpLeosTacacsClientAuthorizationServerResolvedInetAddr OBJECT-TYPE
      SYNTAX       InetAddress
      MAX-ACCESS   read-only
      STATUS       current
      DESCRIPTION
            "Specifies the resolved IP address if wwpLeosTacacsClientAuthorizationServerAddr
             is set to host name.  If wwpLeosTacacsClientAuthorizationServerAddr is set to IP
             address then wwpLeosTacacsClientAuthorizationServerResolvedInetAddr contains
             same information as wwpLeosTacacsClientAuthorizationServerAddr. This OID is used
             in conjunction with wwpLeosTacacsClientAuthorizationServerResolvedInetAddr."
     ::= { wwpLeosTacacsClientAuthorizationServerEntry 20 }

 --
 -- wwpLeosTacacsClientAccountingServerTable
 --
 wwpLeosTacacsClientAccountingServerTable OBJECT-TYPE
     SYNTAX         SEQUENCE OF WwpLeosTacacsClientAccountingServerEntry
     MAX-ACCESS     not-accessible
     STATUS         current
     DESCRIPTION
             "Lists the possible TACACS servers.
              While creating an entry, following objects must be specified:
              wwpLeosTacacsClientAccountingServerStatus, wwpLeosTacacsClientAccountingServerAddr.
              SNMP multiple set operation must be used to create the entry."
     ::= { wwpLeosTacacsClient 16 }

 wwpLeosTacacsClientAccountingServerEntry OBJECT-TYPE
     SYNTAX       WwpLeosTacacsClientAccountingServerEntry
     MAX-ACCESS   not-accessible
     STATUS       current
     DESCRIPTION
             "TACACS server entry."
     INDEX { wwpLeosTacacsClientAccountingServerIndex}
     ::= { wwpLeosTacacsClientAccountingServerTable 1 }
                
 WwpLeosTacacsClientAccountingServerEntry ::= SEQUENCE {
     wwpLeosTacacsClientAccountingServerIndex                       Integer32,     
     wwpLeosTacacsClientAccountingServerAddr                            DisplayString,     
     wwpLeosTacacsClientAccountingServerResolvedAddr                    IpAddress,
     wwpLeosTacacsClientAccountingServerPriority                            Integer32,
     wwpLeosTacacsClientAccountingServerAuthPort                        Integer32,     
     wwpLeosTacacsClientAccountingServerAccessRequests                  Counter32,
     wwpLeosTacacsClientAccountingServerAccessRetransmissions           Counter32,
     wwpLeosTacacsClientAccountingServerAccessAccepts                   Counter32,
     wwpLeosTacacsClientAccountingServerAccessRejects                   Counter32,
     wwpLeosTacacsClientAccountingServerMalformedAccessResponses        Counter32,
     wwpLeosTacacsClientAccountingServerBadAuthenticators               Counter32,
     wwpLeosTacacsClientAccountingServerPendingRequests                 Gauge32,
     wwpLeosTacacsClientAccountingServerTimeouts                        Counter32,
     wwpLeosTacacsClientAccountingServerUnknownTypes                    Counter32,
     wwpLeosTacacsClientAccountingServerBadHeaderSequence               Counter32,    
     wwpLeosTacacsClientAccountingServerStatus                          RowStatus,     
     wwpLeosTacacsClientAccountingServerApplication                         INTEGER,
     wwpLeosTacacsClientAccountingServerClearStatistics                 TruthValue,
     wwpLeosTacacsClientAccountingServerResolvedInetAddrType            InetAddressType,
     wwpLeosTacacsClientAccountingServerResolvedInetAddr                InetAddress
 }

 wwpLeosTacacsClientAccountingServerIndex OBJECT-TYPE
     SYNTAX       Integer32 (1..8)
     MAX-ACCESS   not-accessible
     STATUS       current
     DESCRIPTION
             "Specifies the index of this table."
     ::= { wwpLeosTacacsClientAccountingServerEntry 1 }
        
 wwpLeosTacacsClientAccountingServerAddr OBJECT-TYPE
     SYNTAX       DisplayString (SIZE (0..64))
     MAX-ACCESS   read-write
     STATUS       current
     DESCRIPTION
             "Host name or IP address of the TACACS server."
     ::= { wwpLeosTacacsClientAccountingServerEntry 2 }

 wwpLeosTacacsClientAccountingServerResolvedAddr OBJECT-TYPE
     SYNTAX       IpAddress
     MAX-ACCESS   read-only
     STATUS       current
     DESCRIPTION
	     "When wwpLeosTacacsClientAccountingServerAddr represents:
          Host name    : The resolved address is either the Ipv4 address or Ipv6 address.
          Ipv4 address : The resolved address is the same Ipv4 address.
          Ipv6 address : The resolved address is the same Ipv6 address.
              
          When the resolved address represents:
          Ipv4 address : wwpLeosTacacsClientAccountingServerResolvedAddr represents the resolved Ipv4 address.
          wwpLeosTacacsClientAccountingServerResolvedInetAddr used in conjunction with
          wwpLeosTacacsClientAccountingServerResolvedInetAddrType represents the same Ipv4 address.
          Ipv6 address : wwpLeosTacacsClientAccountingServerResolvedAddr represents 0.0.0.0.
          wwpLeosTacacsClientAccountingServerResolvedInetAddr used in conjunction with
          wwpLeosTacacsClientAccountingServerResolvedInetAddrType represents the Ipv6 address."
     ::= { wwpLeosTacacsClientAccountingServerEntry 3 }
 
  wwpLeosTacacsClientAccountingServerPriority OBJECT-TYPE
     SYNTAX       Integer32
     MAX-ACCESS   read-write
     STATUS       current
     DESCRIPTION
             "Specifies the priority of TACACS servers configured on the device. 
             This is the order in which the servers are accessed."
     ::= { wwpLeosTacacsClientAccountingServerEntry 4 } 

 wwpLeosTacacsClientAccountingServerAuthPort OBJECT-TYPE
      SYNTAX      Integer32 (0..65535)
      MAX-ACCESS  read-write
      STATUS      current
      DESCRIPTION
              "The destination TCP port number to which TACACS
              messages should be sent.  The TACACS server is not
              used for authentication if this port number is 0."
      DEFVAL { 49 }
      ::= { wwpLeosTacacsClientAccountingServerEntry 5 }

-- Request/Response statistics
--
-- TotalIncomingPackets = Accepts + Rejects + UnknownTypes
--
-- TotalIncomingPackets - MalformedResponses - BadAuthenticators -
-- UnknownTypes - PacketsDropped = Successfully received
--
-- AccessRequests + PendingRequests + ClientTimeouts =
-- Successfully Received
--
--

 wwpLeosTacacsClientAccountingServerAccessRequests OBJECT-TYPE
      SYNTAX Counter32
      MAX-ACCESS read-only
      STATUS current
      DESCRIPTION
            "The number of TACACS Access-Request packets sent
             to this server. This does not include retransmissions."
      ::= { wwpLeosTacacsClientAccountingServerEntry 6 }

 wwpLeosTacacsClientAccountingServerAccessRetransmissions OBJECT-TYPE
      SYNTAX Counter32
      MAX-ACCESS read-only
      STATUS current
      DESCRIPTION
            "The number of TACACS Access-Request packets
             retransmitted to this TACACS authentication server."
      ::= { wwpLeosTacacsClientAccountingServerEntry 7 }

 wwpLeosTacacsClientAccountingServerAccessAccepts OBJECT-TYPE
      SYNTAX Counter32
      MAX-ACCESS read-only
      STATUS current
      DESCRIPTION
            "The number of TACACS Access-Accept packets
             (valid or invalid) received from this server."
      ::= { wwpLeosTacacsClientAccountingServerEntry 8 }

 wwpLeosTacacsClientAccountingServerAccessRejects OBJECT-TYPE
      SYNTAX Counter32
      MAX-ACCESS read-only
      STATUS current
      DESCRIPTION
            "The number of TACACS Access-Reject packets
             (valid or invalid) received from this server."
      ::= { wwpLeosTacacsClientAccountingServerEntry  9 }

 -- "Access-Response" includes an Access-Accept, Access-Challenge
 -- or Access-Reject

 wwpLeosTacacsClientAccountingServerMalformedAccessResponses OBJECT-TYPE
      SYNTAX Counter32
      MAX-ACCESS read-only
      STATUS current
      DESCRIPTION
            "The number of malformed TACACS Access-Response
             packets received from this server.
             Malformed packets include packets with
             an invalid length. Bad authenticators or
             Signature attributes or unknown types are not
             included as malformed access responses."
      ::= { wwpLeosTacacsClientAccountingServerEntry 10 }

 wwpLeosTacacsClientAccountingServerBadAuthenticators OBJECT-TYPE
      SYNTAX Counter32
      MAX-ACCESS read-only
      STATUS current
      DESCRIPTION
            "The number of TACACS Access-Response packets
             containing invalid authenticators or Signature
             attributes received from this server."
      ::= { wwpLeosTacacsClientAccountingServerEntry 11 }

 wwpLeosTacacsClientAccountingServerPendingRequests OBJECT-TYPE
      SYNTAX Gauge32
      MAX-ACCESS read-only
      STATUS current
      DESCRIPTION
            "The number of TACACS Access-Request packets
             destined for this server that have not yet timed out
             or received a response. This variable is incremented
             when an Access-Request is sent and decremented due to
             receipt of an Access-Accept, Access-Reject or
             Access-Challenge, a timeout or retransmission."
      ::= { wwpLeosTacacsClientAccountingServerEntry 12 }

 wwpLeosTacacsClientAccountingServerTimeouts OBJECT-TYPE
     SYNTAX Counter32
     MAX-ACCESS read-only
     STATUS current
     DESCRIPTION
            "The number of authentication timeouts to this server.
             After a timeout the client may retry to the same
             server, send to a different server, or
             give up. A retry to the same server is counted as a
             retransmit as well as a timeout. A send to a different
             server is counted as a Request as well as a timeout."
      ::= { wwpLeosTacacsClientAccountingServerEntry  13 }

 wwpLeosTacacsClientAccountingServerUnknownTypes OBJECT-TYPE
      SYNTAX Counter32
      MAX-ACCESS read-only
      STATUS current
      DESCRIPTION
            "The number of TACACS packets of unknown type that
             were received from this server on the authentication port."
      ::= { wwpLeosTacacsClientAccountingServerEntry  14 }

 wwpLeosTacacsClientAccountingServerBadHeaderSequence OBJECT-TYPE
      SYNTAX Counter32
      MAX-ACCESS read-only
      STATUS current
      DESCRIPTION
            "The number of TACACS packets that were
             received from this server on the authentication port
             and dropped for some other reason."
      ::= { wwpLeosTacacsClientAccountingServerEntry  15}
                
 wwpLeosTacacsClientAccountingServerStatus OBJECT-TYPE
      SYNTAX        RowStatus
      MAX-ACCESS    read-create
      STATUS        current
      DESCRIPTION
            "To create a row in this table, set this object to createAndGo(4).

            While creating an entry, the following objects must be specified:
            wwpLeosTacacsClientAccountingServerStatus, wwpLeosTacacsClientAccountingServerAddr.
            SNMP multiple set operation must be used to create the entry.

            To disable a TACACS server, set wwpLeosTacacsClientAccountingServerStatus
            object to 'notInService'."
      ::= { wwpLeosTacacsClientAccountingServerEntry 16 } 

 wwpLeosTacacsClientAccountingServerApplication OBJECT-TYPE
      SYNTAX            INTEGER {
                                        userLogin(1),
                                        dot1x(2),
                                        all(3)   
                                }
      MAX-ACCESS        read-create
      STATUS            deprecated
      DESCRIPTION
            "This object specifies how the TACACS server should be used for authentication.
             Whether this TACACS server should be used for userLogin authentication or dot1x authentication 
             or both is decided by the value of this object. Dot1x is not supported on all platforms."
      DEFVAL    {userLogin}
      ::= { wwpLeosTacacsClientAccountingServerEntry  17}

 wwpLeosTacacsClientAccountingServerClearStatistics OBJECT-TYPE
      SYNTAX            TruthValue
      MAX-ACCESS        read-write
      STATUS            current
      DESCRIPTION
            "This object clears the statistics for a server."
      DEFVAL { false }
      ::= { wwpLeosTacacsClientAccountingServerEntry  18}
 
 wwpLeosTacacsClientAccountingServerResolvedInetAddrType OBJECT-TYPE
      SYNTAX       InetAddressType
      MAX-ACCESS   read-only
      STATUS       current
      DESCRIPTION
	    "Specifies the resolved IP address type.  Used in conjunction with 
             wwpLeosTacacsClientAccountingServerResolvedInetAddr.
             When set to :
             ipv4 : wwpLeosTacacsClientAccountingServerResolvedInetAddr should 
                    be compliant with InetAddressIPv4 
             ipv6 : wwpLeosTacacsClientAccountingServerResolvedInetAddr should 
                    be compliant with InetAddressIPv6."
      ::= { wwpLeosTacacsClientAccountingServerEntry 19 }
  
 wwpLeosTacacsClientAccountingServerResolvedInetAddr OBJECT-TYPE
      SYNTAX       InetAddress
      MAX-ACCESS   read-only
      STATUS       current
      DESCRIPTION
            "Specifies the resolved IP address if wwpLeosTacacsClientAccountingServerAddr
             is set to host name. If wwpLeosTacacsClientAccountingServerAddr is set to IP
             address then wwpLeosTacacsClientAccountingServerResolvedInetAddr contains
             the same information as wwpLeosTacacsClientAccountingServerAddr. This OID is 
             used in conjunction with wwpLeosTacacsClientAccountingServerResolvedInetAddrType."
      ::= { wwpLeosTacacsClientAccountingServerEntry 20 }

--
--
--    
 wwpLeosTacacsClientAccountingSession OBJECT-TYPE     
     SYNTAX        INTEGER {
                        off(1),
                        on(2)
                   }
     MAX-ACCESS    read-write
     STATUS        current
     DESCRIPTION
             "Setting this object turns on session logon/logoff logging with tacacs."
     DEFVAL { off }
     ::= { wwpLeosTacacsClient 20 }

 wwpLeosTacacsClientAccountingCommand OBJECT-TYPE     
     SYNTAX        INTEGER {
                        off(1),
                        on(2)
                   }
     MAX-ACCESS    read-write
     STATUS        current
     DESCRIPTION
             "Setting this object turns on command start/stop logging."
     DEFVAL { off }
     ::= { wwpLeosTacacsClient 21 }

 wwpLeosTacacsClientGlobalServers OBJECT-TYPE     
     SYNTAX        INTEGER {
                        off(1),
                        on(2)
                   }
     MAX-ACCESS    read-write
     STATUS        deprecated
     DESCRIPTION
             "Setting this object turns off global servers."
     DEFVAL { off }
     ::= { wwpLeosTacacsClient 22 }

 wwpLeosTacacsClientSearchMethod OBJECT-TYPE     
     SYNTAX        INTEGER {
                        priority(1),
                        cached(2)
                   }
     MAX-ACCESS    read-write
     STATUS        current
     DESCRIPTION
             "Setting this object sets the search method."
     DEFVAL { priority }
     ::= { wwpLeosTacacsClient 23 }

  wwpLeosTacacsClientKeyMinLen   OBJECT-TYPE
     SYNTAX         Integer32 (2..64)
     MAX-ACCESS     read-write
     STATUS         current
     DESCRIPTION
	     "Setting this object sets the minimum length for TACACS secret key."
     DEFVAL { 8 }
     ::= { wwpLeosTacacsClient 24 } 

 wwpLeosTacacsAuthenticationEnhancedMultiFactor OBJECT-TYPE     
     SYNTAX        INTEGER {
                        off(1),
                        on(2)
                   }
     MAX-ACCESS    read-write
     STATUS        current
     DESCRIPTION
             "Setting this object turns on enhanced multi-factor authentication with TACACS+."
     DEFVAL { off }
     ::= { wwpLeosTacacsClient 25 }

  wwpLeosTacacsClientAuthSecret OBJECT-TYPE
     SYNTAX        OCTET STRING(SIZE(0..259))
     MAX-ACCESS    read-write
     STATUS        current
     DESCRIPTION
             "Sets the pre-encrypted secret to be used for
              TACACS servers. Retrieving the value of this 
              object returns the encrypted secret."
     ::= { wwpLeosTacacsClient 26 }

  wwpLeosTacacsClientPreferredSourceAddress OBJECT-TYPE
     SYNTAX         PreferredSourceAddress
     MAX-ACCESS     read-write
     STATUS         current
     DESCRIPTION
        "Specifies the source address used in TACACS messages originating from the device,
         allowing the default source path address or the loopback interface address."
     DEFVAL { default }
     ::= { wwpLeosTacacsClient 27 } 

  wwpLeosTacacsClientConnectionFailed NOTIFICATION-TYPE
     OBJECTS       { wwpLeosTacacsClientServerResolvedInetAddr,
                     wwpLeosTacacsClientServerResolvedInetAddrType }
     STATUS    current
     DESCRIPTION
        "A wwpLeosTacacsClientConnectionFailed notification is sent if the
         TACACS client is unable to contact the TACACS server."
     ::= { wwpLeosTacacsClientMIBNotifications 1 }

 END

 --
 -- WWP-LEOS-TACACS-CLIENT-MIB
 --
