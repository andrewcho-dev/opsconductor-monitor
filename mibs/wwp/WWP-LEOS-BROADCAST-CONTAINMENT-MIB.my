-- This file was included in WWP MIB release 04-21-05-0007
 --
 -- WWP-LEOS-BROADCAST-CONTAINMENT-MIB.my
 --
 --

 WWP-LEOS-BROADCAST-CONTAINMENT-MIB DEFINITIONS ::= BEGIN

 IMPORTS
   Integer32, Unsigned32, Counter32, Counter64, OBJECT-TYPE, MODULE-IDENTITY, NOTIFICATION-TYPE
   FROM SNMPv2-SMI
   DisplayString, TEXTUAL-CONVENTION, TruthValue, RowStatus
   FROM SNMPv2-TC
   wwpModulesLeos
   FROM WWP-SMI;


 wwpLeosBroadcastContainmentMIB MODULE-IDENTITY
      LAST-UPDATED "201907010000Z"
      ORGANIZATION "Ciena Corp."
      CONTACT-INFO
              "   Mib Meister
                  7035 Ridge Road
                  Hanover, Maryland 21076
                  USA
                  Phone:  +1 800 921 1144
                  Email:  support@ciena.com" 
      DESCRIPTION
              "This MIB module is for the Broadcast containment for WWP Products"

      REVISION    "201907010000Z"
      DESCRIPTION
              "Added new object wwpLeosBroadcastContainmentIgnoreMuticastCfmMessages to support
               bypass of multicast cfm packets filtering by broadcast-containment rules.
               Also added textual convention BroadcastContainmentFlag for
               broadcast-containment settings and updated accordingly for different objects."

      REVISION     "201902110000Z"
      DESCRIPTION
              "Marked WwpLeosBroadcastContainmentCapabilitiesMap as obsolete in lieu of
               WwpLeosBroadcastContainmentFilterMemberCapabilitiesMap.
               Marked wwpLeosBroadcastContainmentCapability as obsolete in lieu of
               wwpLeosBroadcastContainmentFilterMemberCapability.
               Marked wwpLeosBroadcastContainmentPktDroppedStats as obsolete in lieu of
               wwpLeosBroadcastContainmentPacketsDroppedStats to support 64 bit Counters.
               Updated description of wwpLeosBroadcastContainmentBytesDroppedStats.
               Added wwpLeosBroadcastContainmentFilterPacketsDroppedStats and
               wwpLeosBroadcastContainmentFilterBytesDroppedStats to wwpLeosBroadcastContainmentFilterTable
               to display dropped packets and bytes statistics on filter basis.
               Marked wwpLeosBroadcastContainmentFilterMemTable as obsolete in lieu of
               wwpLeosBroadcastContainmentFilterMemberTable which consists information regarding
               broadcast-containment filter members."

      REVISION     "201711150000Z"
      DESCRIPTION
              "Updated contact info."

      REVISION    "201304220000Z"
      DESCRIPTION
              "Miscellaneous spelling and description corrections."

      REVISION    "201203080000Z"
      DESCRIPTION
              "Added wwpLeosBroadcastContainmentIgnoreRapsMessages"

      REVISION    "201203020000Z"               
      DESCRIPTION
              "Added wwpLeosBroadcastContainmentResourceMode and
               wwpLeosBroadcastContainmentBytesDroppedStats"

      REVISION    "200902050000Z"               
      DESCRIPTION
              "Added wwpLeosBroadcastContainmentFilterName to the notification for 
               wwpLeosBcastThresholdExceed and  wwpLeosBcastThresholdNormal."

     REVISION    "200806250000Z"
     DESCRIPTION
              "Defect 25528 - Increase wwpLeosBroadcastContainmentFilterName octet
               length to 16 characters (15 plus a null byte)."

      REVISION    "200806182100Z"
      DESCRIPTION
               "Add new objects to support global enable/disable and time setting"

      REVISION    "200706022100Z"
      DESCRIPTION
              "Initial creation."

      ::= { wwpModulesLeos 8 }


 --
 -- Textual Conventions
 --
 BroadcastContainmentFlag ::=  TEXTUAL-CONVENTION
     STATUS  current
     DESCRIPTION
             "This textual convention enumerates the flag value for
              broadcast-containment settings."
     SYNTAX  INTEGER
             {
                enable(1),
                disable(2)
             }

 --
 -- Node definitions
 --
	
 wwpLeosBroadcastContainmentMIBObjects OBJECT IDENTIFIER ::= { wwpLeosBroadcastContainmentMIB 1 }
 
  -- Notifications 
  
 wwpLeosBroadcastContainmentMIBNotificationPrefix  OBJECT IDENTIFIER ::= { wwpLeosBroadcastContainmentMIB 2 } 
 wwpLeosBroadcastContainmentMIBNotifications  OBJECT IDENTIFIER ::= { wwpLeosBroadcastContainmentMIBNotificationPrefix 1 } 
 
 -- Conformance information 
 
 wwpLeosBroadcastContainmentMIBConformance OBJECT IDENTIFIER ::= { wwpLeosBroadcastContainmentMIB 3 } 
 wwpLeosBroadcastContainmentMIBCompliances OBJECT IDENTIFIER ::= { wwpLeosBroadcastContainmentMIBConformance 1 } 		
 wwpLeosBroadcastContainmentMIGroups      OBJECT IDENTIFIER ::= { wwpLeosBroadcastContainmentMIBConformance 2 }

 WwpLeosBroadcastContainmentCapabilitiesMap ::= TEXTUAL-CONVENTION
	STATUS          obsolete
	DESCRIPTION
		"This bit mask shows the capability of the device. It shows that which index is valid
		 wwpLeosBroadcastContainmentVlanId or wwpLeosBroadcastContainmentPortId"
	SYNTAX BITS {
			wwpLeosBroadcastContainmentVlanId(0),
			wwpLeosBroadcastContainmentPortId(1)			
	}

 WwpLeosBroadcastContainmentFilterMemberCapabilitiesMap ::= TEXTUAL-CONVENTION
	STATUS          current
	DESCRIPTION
		"This bit mask indicates the type of memberships that Broadcast Filter supports.
                 If wwpLeosBroadcastContainmentFilterMemberPerPortPerVs is set then Port X VS 
                 can be added as a member to Broadcast Containment Filter.
                 If wwpLeosBroadcastContainmentFilterMemberPort is set then Port can be added
                 as a member to Broadcast Containment Filter."
        SYNTAX          BITS {
                        wwpLeosBroadcastContainmentFilterMemberPerPortPerVs(1),
                        wwpLeosBroadcastContainmentFilterMemberPort(2)
	}
--
-- Global information
-- 
 
 wwpLeosBroadcastContainmentCapability OBJECT-TYPE
      SYNTAX		WwpLeosBroadcastContainmentCapabilitiesMap
      MAX-ACCESS	read-only
      STATUS		obsolete
      DESCRIPTION
	      "It shows which of the following (wwpLeosBroadcastContainmentPortId or wwpLeosBroadcastContainmentVlanId or both) can
	       be used as an index in wwpLeosBroadcastContainmentFilterMemTable. If bit 0 of the bit mask (starting from right to left) 
	       is set to 1 then wwpLeosBroadcastContainmentVlanId can be used as index. If bit 1 of the bit mask is set to 1 then 
	       wwpLeosBroadcastContainmentPortId can be used as index. If both bits are set to 1 then both can be used as index."
      ::= { wwpLeosBroadcastContainmentMIBObjects 1 }

 wwpLeosBroadcastContainmentPktDroppedStats	OBJECT-TYPE
      SYNTAX		Counter32
      MAX-ACCESS	read-only
      STATUS		obsolete
      DESCRIPTION
	      "Displays the global dropped packets statistics for all VLANs and ports."
      ::= { wwpLeosBroadcastContainmentMIBObjects 2 }

 wwpLeosBroadcastContainmentGlobalStatus     OBJECT-TYPE
     SYNTAX          INTEGER {
                         enable(1),
		         disable(2)
		     }
     MAX-ACCESS      read-write
     STATUS          current
     DESCRIPTION
    	     "Setting this object to 'enable' globally enables
    	      broadcast-containment on the device. The default is enabled."
     ::= { wwpLeosBroadcastContainmentMIBObjects 6  } 
      
 wwpLeosBroadcastContainmentGlobalTime  OBJECT-TYPE
     SYNTAX          Integer32(10..2560)
     UNITS           "milli-seconds"
     MAX-ACCESS      read-write
     STATUS          current     
     DESCRIPTION
             "The global broadcast containment sample or 
              integration time. The default is 100ms."
     ::= { wwpLeosBroadcastContainmentMIBObjects 7 }

 wwpLeosBroadcastContainmentIgnoreRapsMessages     OBJECT-TYPE
     SYNTAX          INTEGER {
                         enable(1),
                         disable(2)
		     }
     MAX-ACCESS      read-write
     STATUS          current
     DESCRIPTION
            "When this object is enabled, all configured broadcast
             containment filters will ignore R-APS messages when
             filtering PDUs.  The default setting is disabled."
     ::= { wwpLeosBroadcastContainmentMIBObjects 8  } 

 wwpLeosBroadcastContainmentResourceMode  OBJECT-TYPE
     SYNTAX          INTEGER {
                         enable(1),
                         disable(2)
                     }     
     MAX-ACCESS      read-write
     STATUS          current     
     DESCRIPTION
             "Selects whether broadcast containment uses resource manager
              resources. The selection of containment classification is
              more limited when resource mode is disabled."
     ::= { wwpLeosBroadcastContainmentMIBObjects 9 }

 wwpLeosBroadcastContainmentBytesDroppedStats OBJECT-TYPE
      SYNTAX        Counter64
      MAX-ACCESS    read-only
      STATUS        current
      DESCRIPTION
          "Displays the global dropped bytes count."
      ::= { wwpLeosBroadcastContainmentMIBObjects 10 }

 wwpLeosBroadcastContainmentPacketsDroppedStats OBJECT-TYPE
      SYNTAX        Counter64
      MAX-ACCESS    read-only
      STATUS        current
      DESCRIPTION
          "Displays the global dropped packets count."
      ::= { wwpLeosBroadcastContainmentMIBObjects 11 }

 wwpLeosBroadcastContainmentFilterMemberCapability    OBJECT-TYPE
      SYNTAX        WwpLeosBroadcastContainmentFilterMemberCapabilitiesMap
      MAX-ACCESS    read-only
      STATUS        current
      DESCRIPTION
		"This bit mask indicates the type of memberships that Broadcast Filter supports.
                 If wwpLeosBroadcastContainmentFilterMemberPerPortPerVs is set then Port X VS 
                 can be added as a member to Broadcast Containment Filter.
                 If wwpLeosBroadcastContainmentFilterMemberPort is set then Port can be added
                 as a member to Broadcast Containment Filter."
      ::= { wwpLeosBroadcastContainmentMIBObjects 12 }

 wwpLeosBroadcastContainmentIgnoreMulticastCfmMessages OBJECT-TYPE
     SYNTAX          BroadcastContainmentFlag
     MAX-ACCESS      read-write
     STATUS          current
     DESCRIPTION
            "When this object is enabled, all configured broadcast
             containment filters will ignore multicast cfm messages when
             filtering PDUs.  The default setting is disabled."
     ::= { wwpLeosBroadcastContainmentMIBObjects 14 } 
--
-- Filter table information
-- 
  
 wwpLeosBroadcastContainmentFilterTable OBJECT-TYPE
     SYNTAX       SEQUENCE OF WwpLeosBroadcastContainmentFilterEntry
     MAX-ACCESS   not-accessible
     STATUS       current
     DESCRIPTION
	     "Table of broadcast containment configuration."
     ::= { wwpLeosBroadcastContainmentMIBObjects 4 }
 		
 wwpLeosBroadcastContainmentFilterEntry OBJECT-TYPE
     SYNTAX       WwpLeosBroadcastContainmentFilterEntry
     MAX-ACCESS   not-accessible
     STATUS       current
     DESCRIPTION
	     "Broadcast containment entry in the Broadcast Containment Table."
     INDEX { wwpLeosBroadcastContainmentIndex }
     ::= { wwpLeosBroadcastContainmentFilterTable 1 } 

 WwpLeosBroadcastContainmentFilterEntry ::= SEQUENCE { 
     wwpLeosBroadcastContainmentIndex                      Integer32,
     wwpLeosBroadcastContainmentFilterName                 DisplayString,
     wwpLeosBroadcastContainmentPktLimit                   Integer32,     
     wwpLeosBroadcastContainmentPktDropState               TruthValue,
     wwpLeosBroadcastContainmentStatus                     RowStatus,
     wwpLeosBroadcastContainmentKbps                       Integer32,
     wwpLeosBroadcastContainmentClassifier                 Unsigned32,
     wwpLeosBroadcastContainmentFilterPacketsDroppedStats  Counter64,
     wwpLeosBroadcastContainmentFilterBytesDroppedStats    Counter64
 }
 
 wwpLeosBroadcastContainmentIndex OBJECT-TYPE
      SYNTAX		Integer32 (1..4095)
      MAX-ACCESS	read-only
      STATUS		current
      DESCRIPTION
	      "Unique index into the table."
      ::= { wwpLeosBroadcastContainmentFilterEntry 1 }
 
 wwpLeosBroadcastContainmentFilterName OBJECT-TYPE
      SYNTAX      DisplayString (SIZE (1..15))
      MAX-ACCESS	read-create
      STATUS		current
      DESCRIPTION
	      "Specifies the name of the filter. If wwpLeosBroadcastContainmentFilterName is not set during  
	       filter creation then filter will be created with no name. 
	       Filter name can be set later by setting this object."
      ::= { wwpLeosBroadcastContainmentFilterEntry 2 }
  
 wwpLeosBroadcastContainmentPktLimit OBJECT-TYPE
     SYNTAX      Integer32 (0..104856000)
     MAX-ACCESS  read-create
     STATUS      current
     DESCRIPTION
             "The maximum number of broadcast packets which can be
	     received by this device. Setting this object to 0 sets the
	     broadcast packet limit to unlimited."
     DEFVAL { 0 }
     ::= { wwpLeosBroadcastContainmentFilterEntry 3 }
 
 wwpLeosBroadcastContainmentPktDropState OBJECT-TYPE
      SYNTAX		TruthValue
      MAX-ACCESS	read-only
      STATUS		current
      DESCRIPTION
	      "This object if True, specifies that packets were dropped for the
	       given filter since it was last read. If this object is false
	       then no packet was dropped since it was last read."
      ::= { wwpLeosBroadcastContainmentFilterEntry 4 }

 wwpLeosBroadcastContainmentStatus OBJECT-TYPE
     SYNTAX      RowStatus
     MAX-ACCESS  read-create
     STATUS      current
     DESCRIPTION
	     "To create a row in this table, a manager must
	      set this object to 'createAndGo'. To delete the
	      entry set to 'destroy'. To update this entry
	      this object may not be set."
     ::= { wwpLeosBroadcastContainmentFilterEntry 5 }
     
  wwpLeosBroadcastContainmentKbps  OBJECT-TYPE
     SYNTAX      Integer32 (0..10000000)
     MAX-ACCESS  read-create
     STATUS      current
     DESCRIPTION
	     "The maximum number of broadcast packets that can be
	     received by this device."
     ::= { wwpLeosBroadcastContainmentFilterEntry 6 }   
     
  wwpLeosBroadcastContainmentClassifier   OBJECT-TYPE
  	 SYNTAX			Unsigned32
  	 MAX-ACCESS		read-create
  	 STATUS			current
  	 DESCRIPTION
        "The classifier type for the filter. The value of this object can be
         any combination of the following:

         ClassifierType_Unknown(0)
         ClassifierType_Broadcast(1)
         ClassifierType_UnknownL2Multicast(2)
         ClassifierType_UnknownUnicast(4)
         ClassifierType_UnknownIpMulticast(8)
         ClassifierType_AllMultcast(16)

        For example, if the user wants to set the classifier type for the
        filter as broadcast+unknown_unicast, the value of the
        object should be set as 5 (1 + 4). Similary if the preferred classifier
        type is All_flooding, the value would be 15 (1+2+4+8).  By default, the
        classifier type is 3 (broadcast + unknownL2Multicast).
        
        When resource mode is disabled, the only supported multicast option
        is ClassifierType_AllMulticast. The L2 and IP multicast options are
        controlled individually if resource mode is enabled."
  	 DEFVAL			{3}
  	 ::= { wwpLeosBroadcastContainmentFilterEntry	7 }

 wwpLeosBroadcastContainmentFilterPacketsDroppedStats        OBJECT-TYPE
      SYNTAX            Counter64
      MAX-ACCESS        read-only
      STATUS            current
      DESCRIPTION
	      "Displays the filter dropped packets statistics."
      ::= { wwpLeosBroadcastContainmentFilterEntry      8 }

 wwpLeosBroadcastContainmentFilterBytesDroppedStats          OBJECT-TYPE
      SYNTAX            Counter64
      MAX-ACCESS        read-only
      STATUS            current
      DESCRIPTION
          "Displays the filter dropped bytes statistics."
      ::= { wwpLeosBroadcastContainmentFilterEntry      9 }
--
-- Filter member table
-- 

 wwpLeosBroadcastContainmentFilterMemTable OBJECT-TYPE
     SYNTAX       SEQUENCE OF WwpLeosBroadcastContainmentFilterMemEntry
     MAX-ACCESS   not-accessible
     STATUS       obsolete
     DESCRIPTION
	     "Table of broadcast containment membership."
     ::= { wwpLeosBroadcastContainmentMIBObjects 5 }
 		
 wwpLeosBroadcastContainmentFilterMemEntry OBJECT-TYPE
     SYNTAX       WwpLeosBroadcastContainmentFilterMemEntry
     MAX-ACCESS   not-accessible
     STATUS       obsolete
     DESCRIPTION
	     "Broadcast containment entry in the Broadcast Containment Table."
     INDEX { wwpLeosBroadcastContainmentIndex, wwpLeosBroadcastContainmentVlanId, wwpLeosBroadcastContainmentPortId }
     ::= { wwpLeosBroadcastContainmentFilterMemTable 1 } 

 WwpLeosBroadcastContainmentFilterMemEntry ::= SEQUENCE { 
     wwpLeosBroadcastContainmentVlanId		Integer32,
     wwpLeosBroadcastContainmentPortId		Integer32,     
     wwpLeosBroadcastContainmentFilterMemStatus	RowStatus
 }
 
 wwpLeosBroadcastContainmentVlanId OBJECT-TYPE
      SYNTAX 		Integer32 (0..4095)
      MAX-ACCESS	not-accessible
      STATUS            obsolete
      DESCRIPTION
	      "Unique index into the table. Depending on the capability of the device,
	       set this index to valid VLAN id or 0 for all vlans."
      ::= { wwpLeosBroadcastContainmentFilterMemEntry 1 }
 
 wwpLeosBroadcastContainmentPortId OBJECT-TYPE
      SYNTAX Integer32 (0..4095)
      MAX-ACCESS       not-accessible
      STATUS           obsolete
      DESCRIPTION
	      "Unique index into the table. Depending on the capability of the device,
	       set this index to valid port id or 0 for all ports."
      ::= { wwpLeosBroadcastContainmentFilterMemEntry 2 }  
 
 wwpLeosBroadcastContainmentFilterMemStatus OBJECT-TYPE
     SYNTAX      RowStatus
     MAX-ACCESS  read-create
     STATUS      obsolete
     DESCRIPTION
	     "To create a row in this table, a manager must
	      set this object to 'createAndGo'. To delete the 
	      entry set to 'destroy'. To update this entry
	      this object may not be set."
     ::= { wwpLeosBroadcastContainmentFilterMemEntry 3 }

 wwpLeosBroadcastContainmentFilterMemberTable OBJECT-TYPE
     SYNTAX       SEQUENCE OF WwpLeosBroadcastContainmentFilterMemberEntry
     MAX-ACCESS   not-accessible
     STATUS       current
     DESCRIPTION
	     "Table contains information regarding members of broadcast containment filters.
              Currently this table supports only get operation."
     ::= { wwpLeosBroadcastContainmentMIBObjects 13 }
 		
 wwpLeosBroadcastContainmentFilterMemberEntry OBJECT-TYPE
     SYNTAX       WwpLeosBroadcastContainmentFilterMemberEntry
     MAX-ACCESS   not-accessible
     STATUS       current
     DESCRIPTION
	     "Member Entry of a Broadcast containment Filter."
     INDEX { wwpLeosBroadcastContainmentIndex,
             wwpLeosBroadcastContainmentFilterMemberPortId,
             wwpLeosBroadcastContainmentFilterMemberVsIndex }
     ::= { wwpLeosBroadcastContainmentFilterMemberTable 1 } 

 WwpLeosBroadcastContainmentFilterMemberEntry ::= SEQUENCE {
     wwpLeosBroadcastContainmentFilterMemberPortId    Integer32,
     wwpLeosBroadcastContainmentFilterMemberVsIndex   Integer32,
     wwpLeosBroadcastContainmentFilterMemberStatus    RowStatus
 }
 
 wwpLeosBroadcastContainmentFilterMemberPortId OBJECT-TYPE
      SYNTAX           Integer32 (0..4095)
      MAX-ACCESS       not-accessible
      STATUS           current
      DESCRIPTION
              "This object specifies the port id that is used as a unique
               index in the table."
      ::= { wwpLeosBroadcastContainmentFilterMemberEntry 1 }
 
 wwpLeosBroadcastContainmentFilterMemberVsIndex OBJECT-TYPE
      SYNTAX           Integer32 (0..65535)
      MAX-ACCESS       not-accessible
      STATUS           current
      DESCRIPTION
              "This object specifies the virtual switch index that is used as a unique
               index in the table."
      ::= { wwpLeosBroadcastContainmentFilterMemberEntry 2 }

 wwpLeosBroadcastContainmentFilterMemberStatus OBJECT-TYPE
     SYNTAX            RowStatus
     MAX-ACCESS        read-create
     STATUS            current
     DESCRIPTION
	     "To create a row in this table, a manager must
	      set this object to 'createAndGo'. To delete the 
	      entry set to 'destroy'. To update this entry
	      this object may not be set."
     ::= { wwpLeosBroadcastContainmentFilterMemberEntry 3 }

--
-- Notifications
-- 

 wwpLeosBcastThresholdExceed  NOTIFICATION-TYPE
        OBJECTS	   {
			wwpLeosBroadcastContainmentIndex,
                        wwpLeosBroadcastContainmentFilterName

		   }
        STATUS	   current
	DESCRIPTION
		"A wwpLeosBcastThresholdExceed notification is sent
		when for given filter index, the number of broadcast
		packet received becomes greater than or equal to the
		configured packet limit, and the value of broadcast packet
		received at the last sampling interval was less than
		the configured packet limit."
	::= { wwpLeosBroadcastContainmentMIBNotifications 1 }
	
 wwpLeosBcastThresholdNormal  NOTIFICATION-TYPE
	OBJECTS	   {
			wwpLeosBroadcastContainmentIndex,
                        wwpLeosBroadcastContainmentFilterName
		   }
        STATUS	   current
	DESCRIPTION
	        "A wwpLeosBcastThresholdNormal notification is sent
		when for given filter index, the total number of
		broadcast packet received becomes less than the
		configured packet limit, and the value of broadcast
		packet received at the last sampling interval
		was greater than or equal to the configured packet limit." 
	::= { wwpLeosBroadcastContainmentMIBNotifications 2 }
	

 END
