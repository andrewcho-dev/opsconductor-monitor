-- This file was included in WWP MIB release 04-21-05-0007
 --
 -- WWP-LEOS-USER-MIB.my
 --
 --

 WWP-LEOS-USER-MIB DEFINITIONS ::= BEGIN

 IMPORTS
   Integer32, Unsigned32, Counter32, OBJECT-TYPE, MODULE-IDENTITY
       FROM SNMPv2-SMI
   RowStatus, DisplayString, TruthValue
       FROM SNMPv2-TC
   wwpModulesLeos
       FROM WWP-SMI;


 wwpLeosUserMIB MODULE-IDENTITY
       LAST-UPDATED "202409030000Z"
       ORGANIZATION "Ciena Corp."
       CONTACT-INFO
          "   Mib Meister
              7035 Ridge Road
              Hanover, Maryland 21076
              USA
              Phone:  +1 800 921 1144
              Email:  support@ciena.com"

       DESCRIPTION
                    "This MIB module defines the generic managed objects
                     for User Information on WWP devices."

       REVISION     "202409030000Z"
       DESCRIPTION
                    "Added a new object wwpLeosUserFallbackAdminState."
       REVISION     "201711150000Z"
       DESCRIPTION
                    "Updated contact info."
        REVISION    "201708110000Z"
        DESCRIPTION
                    "Added comment for wwpLeosUserUID - a value of 0 during user create
                     will auto assign a User UID."
        REVISION    "201508310000Z"
        DESCRIPTION
                    "Added a new object wwpLeosUserMinimumUsernameLength."
        REVISION    "201504010000Z"
        DESCRIPTION
                    "Added objects to read and write the user password
                     complexity requirements.
                     Corrected the MAX-ACCESS of wwpLeosUserWhoStatus."
        REVISION    "201410100000Z"
        DESCRIPTION
                    "Defined wwpLeosUserConfiguration branch.
                     Defined wwpLeosUserMinimumPasswordLength object.
                     Increased maximum length of wwpLeosUserPassword to 128."
        REVISION    "201306130000Z"
        DESCRIPTION
                    "Deprecated  wwpLeosUserIsDefault, and wwpLeosUserIsModified.
                    Corrected description on wwpLeosUserIsEncrypted."
        REVISION    "201304230000Z"
        DESCRIPTION
                    "Miscellaneous spelling and description corrections."
        REVISION  "201207110000Z"
        DESCRIPTION
                    "Changed the definitions of the wwpLeosUserPrivLevel
                    values to match those used internally and at the CLI."
        REVISION    "201206270000Z"
        DESCRIPTION
                    "Corrected string lengths."
        REVISION  "201107060000Z"
        DESCRIPTION
                    " Added a new object wwpLeosUserAuthProviderScope."
        REVISION    "200703010000Z"
        DESCRIPTION
                    "Initial creation."
        ::= { wwpModulesLeos 39 }

 --
 -- Node definitions
 --
	
 wwpLeosUserMIBObjects 	OBJECT IDENTIFIER ::= { wwpLeosUserMIB 1 }
 wwpLeosUser 			OBJECT IDENTIFIER ::= { wwpLeosUserMIBObjects 1 }
 
 --
 -- Notifications 
 --
  
 wwpLeosUserMIBNotificationPrefix	OBJECT IDENTIFIER ::= { wwpLeosUserMIB 2 } 
 wwpLeosUserMIBNotifications    	OBJECT IDENTIFIER ::= { wwpLeosUserMIBNotificationPrefix 0 }

 --
 -- Conformance information 
 --
 
 wwpLeosUserMIBConformance 	OBJECT IDENTIFIER ::= { wwpLeosUserMIB 3 } 
 wwpLeosUserMIBCompliances 	OBJECT IDENTIFIER ::= { wwpLeosUserMIBConformance 1 } 		
 wwpLeosUserMIBGroups      	OBJECT IDENTIFIER ::= { wwpLeosUserMIBConformance 2 }

 wwpLeosUserAuthProviderTable OBJECT-TYPE
     	SYNTAX       SEQUENCE OF WwpLeosUserAuthProviderEntry
     	MAX-ACCESS   not-accessible
     	STATUS       current
     	DESCRIPTION	 "Table of UserAuth Providers."
     	::= { wwpLeosUser 1 }
		
 wwpLeosUserAuthProviderEntry OBJECT-TYPE
     	SYNTAX       WwpLeosUserAuthProviderEntry
     	MAX-ACCESS   not-accessible
     	STATUS       current
     	DESCRIPTION	  "An entry for each user authentication provider."
     	INDEX { wwpLeosUserAuthProviderPriority }
     	::= { wwpLeosUserAuthProviderTable 1 }
		 
 WwpLeosUserAuthProviderEntry ::= SEQUENCE { 
     	wwpLeosUserAuthProviderPriority		Integer32,
     	wwpLeosUserAuthProviderType			INTEGER,
     	wwpLeosUserAuthProviderCalled		Unsigned32,
     	wwpLeosUserAuthProviderSuccess		Unsigned32,
     	wwpLeosUserAuthProviderFailure    	Unsigned32,
        wwpLeosUserAuthProviderSkipped          Unsigned32,
        wwpLeosUserAuthProviderScope            INTEGER
 }

 wwpLeosUserAuthProviderPriority OBJECT-TYPE
     	SYNTAX     		Integer32 (1..2)
     	MAX-ACCESS   	not-accessible
     	STATUS       	current
     	DESCRIPTION	   	"The priority of this user authentication provider."
     	::= { wwpLeosUserAuthProviderEntry 1 }
		
 wwpLeosUserAuthProviderType OBJECT-TYPE
 		SYNTAX			INTEGER {
 							none	(1),	-- No Method Configured
 							local	(2),	-- Local Authentication
 							radius	(3),	-- Radius Authentication
 							tacacs	(4)	-- Tacacs Authentication
 						}
     	MAX-ACCESS  	read-write
     	STATUS      	current
     	DESCRIPTION	  	"The type/method of this user authentication provider.
     					 At least one entry must be a provider other than 'none'
     					 and any given provider may not be used twice.  When a
     					 provider is changed to 'none', lower priority providers
     					 have their priority increased to close the gap."
     	::= { wwpLeosUserAuthProviderEntry 2 }
     	
 wwpLeosUserAuthProviderCalled OBJECT-TYPE
 		SYNTAX			Unsigned32
 		MAX-ACCESS		read-write
 		STATUS			current
 		DESCRIPTION		"The number of calls to this user authentication provider.
 						 The counter is cleared automatically when AuthProviderType
 						 is changed or can be cleared manually." 
 		::= { wwpLeosUserAuthProviderEntry 3 }
 
  wwpLeosUserAuthProviderSuccess OBJECT-TYPE
 		SYNTAX			Unsigned32
 		MAX-ACCESS		read-write
 		STATUS			current
 		DESCRIPTION		"The number of times this user authentication provider returned
 						 a Success response.  The counter is cleared automatically when
 						 AuthProviderType is changed or can be cleared manually." 
 		::= { wwpLeosUserAuthProviderEntry 4 }
 
 wwpLeosUserAuthProviderFailure OBJECT-TYPE
 		SYNTAX			Unsigned32
 		MAX-ACCESS		read-write
 		STATUS			current
 		DESCRIPTION		"The number of times this user authentication provider returned
 						 a Failure response.  The counter is cleared automatically when
 						 AuthProviderType is changed or can be cleared manually." 
 		::= { wwpLeosUserAuthProviderEntry 5 }
 
 wwpLeosUserAuthProviderSkipped OBJECT-TYPE
 		SYNTAX			Unsigned32
 		MAX-ACCESS		read-write
 		STATUS			current
 		DESCRIPTION		"The number of times this user authentication provider returned
 						 a Skip Me response.  The counter is cleared automatically when
 						 AuthProviderType is changed or can be cleared manually." 
 		::= { wwpLeosUserAuthProviderEntry 6 }
                 
 wwpLeosUserAuthProviderScope OBJECT-TYPE
                SYNTAX                  INTEGER
                                        {
                                                none (0),
                                                serial (1),
                                                remote (2),
                                                all    (3)
                                        }

                MAX-ACCESS              read-write
                STATUS                  current
                DESCRIPTION             "The scope to be used for each authentication method." 
                DEFVAL                 { all }
                ::= { wwpLeosUserAuthProviderEntry 7 }
                                 
 wwpLeosUserWhoTable OBJECT-TYPE
     	SYNTAX       SEQUENCE OF WwpLeosUserWhoEntry
     	MAX-ACCESS   not-accessible
     	STATUS       current
     	DESCRIPTION	 "Table of logged in users."
     	::= { wwpLeosUser 2 }
		
 wwpLeosUserWhoEntry OBJECT-TYPE
     	SYNTAX       WwpLeosUserWhoEntry
     	MAX-ACCESS   not-accessible
     	STATUS       current
     	DESCRIPTION	  "An entry for each logged in user."
     	INDEX { wwpLeosUserWhoPid }
     	::= { wwpLeosUserWhoTable 1 }
		 
 WwpLeosUserWhoEntry ::= SEQUENCE { 
     	wwpLeosUserWhoPid					Unsigned32,
     	wwpLeosUserWhoUser					DisplayString,
     	wwpLeosUserWhoTerminal				DisplayString,
     	wwpLeosUserWhoIdleTime				Counter32,
     	wwpLeosUserWhoStatus				RowStatus
 }

 wwpLeosUserWhoPid OBJECT-TYPE
     	SYNTAX     		Unsigned32
     	MAX-ACCESS   	not-accessible
     	STATUS       	current
     	DESCRIPTION	   	"The pid of the users shell process."
     	::= { wwpLeosUserWhoEntry 1 } 
     	
 wwpLeosUserWhoUser OBJECT-TYPE
 		SYNTAX			DisplayString(SIZE(0..32))
 		MAX-ACCESS		read-only
 		STATUS			current
 		DESCRIPTION		"The username used during login authentication."
 		::= { wwpLeosUserWhoEntry 2 }
 		
 wwpLeosUserWhoTerminal OBJECT-TYPE
 		SYNTAX			DisplayString(SIZE(0..64))
 		MAX-ACCESS		read-only
 		STATUS			current
 		DESCRIPTION		"The terminal from which the user logged in."
 		::= { wwpLeosUserWhoEntry 3 }
 		
 wwpLeosUserWhoIdleTime OBJECT-TYPE
 		SYNTAX			Counter32
 		MAX-ACCESS		read-only
 		STATUS			current
 		DESCRIPTION		"The users idle time in minutes.  This counter is reset to
 						 zero when the shell process detects input from the user."
 		::= { wwpLeosUserWhoEntry 4 }     
 		
 wwpLeosUserWhoStatus OBJECT-TYPE
 		SYNTAX			RowStatus
 		MAX-ACCESS		read-create
 		STATUS			current
 		DESCRIPTION		"Status of the users shell process.  To kill a users
 						shell, set this object to 'Destroy'.  No other value
                        is accepted."
 		::= { wwpLeosUserWhoEntry 5 }
                                
 wwpLeosUserTable OBJECT-TYPE
 		SYNTAX			SEQUENCE OF WwpLeosUserEntry
 		MAX-ACCESS		not-accessible
 		STATUS			current
 		DESCRIPTION		"Table of locally configured users."
 		::= { wwpLeosUser 3 }
 		
 wwpLeosUserEntry OBJECT-TYPE
 		SYNTAX			WwpLeosUserEntry
 		MAX-ACCESS		not-accessible
 		STATUS			current
 		DESCRIPTION		"An entry for each user in the local password file."
 		INDEX { wwpLeosUserUid }
 		::= { wwpLeosUserTable 1 }
 		
 WwpLeosUserEntry ::= SEQUENCE { 
 		wwpLeosUserUid				Unsigned32,
 		wwpLeosUserName				DisplayString,
 		wwpLeosUserPassword			DisplayString,
 		wwpLeosUserPrivLevel		INTEGER,
 		wwpLeosUserIsDefault		TruthValue,
 		wwpLeosUserIsEncrypted		TruthValue,
 		wwpLeosUserIsModified		TruthValue,
 		wwpLeosUserStatus			RowStatus
 } 
 
 wwpLeosUserUid OBJECT-TYPE
 		SYNTAX			Unsigned32
 		MAX-ACCESS		not-accessible
 		STATUS			current
 		DESCRIPTION		"The numeric user ID of the user.  These numbers are generated
 						by the device in order to make indexing the table easy, but
 						they are not tied to specific user names during a reboot.  When
 						a new user is created, the user ID must be an unused value.
                  For CreateAndGo, a value of 0 tells the system to auto-assign the user ID"
 		::= { wwpLeosUserEntry 1 }
 		
 wwpLeosUserName OBJECT-TYPE
 		SYNTAX			DisplayString(SIZE(1..32))
 		MAX-ACCESS		read-create
 		STATUS			current
 		DESCRIPTION		"The name of the user."
 		::= { wwpLeosUserEntry 2 }
 		
 wwpLeosUserPassword OBJECT-TYPE
 		SYNTAX			DisplayString(SIZE(0..128))
 		MAX-ACCESS		read-create
 		STATUS			current
 		DESCRIPTION		"The users password in encrypted form.  When setting this object
 						 set wwpLeosUserIsEncrypted at the same time in order to
 						 specify whether the password being set needs to be encrypted
 						 by the device or whether it is already encrypted."
 		::= { wwpLeosUserEntry 3 }
 		
 wwpLeosUserPrivLevel OBJECT-TYPE
 		SYNTAX			INTEGER {
 							none	(0),	-- No Privileges
 							limited	(1),	-- Read-Only Privileges
 							admin	(2),	-- Admin, Read-Write Privileges
 							super	(3),	-- Super User, Read-Write-Create Privileges
 							diag	(4) 	-- Diagnostic, Unrestricted Privileges
 						}
 		MAX-ACCESS		read-create
 		STATUS			current
 		DESCRIPTION		"The privilege level of the user."
 		::= { wwpLeosUserEntry 4 }
 		
 wwpLeosUserIsDefault OBJECT-TYPE
 		SYNTAX			TruthValue
 		MAX-ACCESS		read-only
 		STATUS			deprecated
 		DESCRIPTION		"Entry is no longer supported for security reasons and will always return False."
 		::= { wwpLeosUserEntry 5 }
 		
 wwpLeosUserIsEncrypted OBJECT-TYPE
 		SYNTAX			TruthValue
 		MAX-ACCESS		read-create
 		STATUS			current
 		DESCRIPTION		"This is always True on a Get since the password is always
 						stored locally on the device in encrypted form.  During a Set,
 						it is False if you are sending wwpLeosUserPassword in the clear
 						so the device can encrypt it, or True if wwpLeosUserPassword is
 						already in encrypted form."
 		::= { wwpLeosUserEntry 6 }
 		
 wwpLeosUserIsModified OBJECT-TYPE
 		SYNTAX			TruthValue
 		MAX-ACCESS		read-only
 		STATUS			deprecated
 		DESCRIPTION		"Entry is no longer supported for security reasons and will always return False."
 		::= { wwpLeosUserEntry 7 } 
 		
 wwpLeosUserStatus		OBJECT-TYPE
 		SYNTAX			RowStatus
 		MAX-ACCESS		read-create
 		STATUS			current
 		DESCRIPTION		"Use CreateAndGo to create a new user, Destroy to remove a user."
 		::= { wwpLeosUserEntry 8 }

 wwpLeosUserConfiguration    OBJECT IDENTIFIER ::= { wwpLeosUser 4 }

 wwpLeosUserMinimumPasswordLength  OBJECT-TYPE
    SYNTAX      Unsigned32 (0..128)
    MAX-ACCESS  read-write
    STATUS      current
    DESCRIPTION "This object specifies the minimum number of characters that
                 must be specified when setting the password of a
                 locally-authenticated user."
    DEFVAL      { 0 }
    ::= { wwpLeosUserConfiguration 1 }

 wwpLeosUserPasswordMinimumLowercaseChars  OBJECT-TYPE
    SYNTAX      Unsigned32 (0..128)
    MAX-ACCESS  read-write
    STATUS      current
    DESCRIPTION "This object specifies the minimum number of lowercase
                 characters that must be specified when setting the password
                 of a locally-authenticated user."
    DEFVAL      { 0 }
    ::= { wwpLeosUserConfiguration 2 }

 wwpLeosUserPasswordMinimumUppercaseChars  OBJECT-TYPE
    SYNTAX      Unsigned32 (0..128)
    MAX-ACCESS  read-write
    STATUS      current
    DESCRIPTION "This object specifies the minimum number of uppercase
                 characters that must be specified when setting the password
                 of a locally-authenticated user."
    DEFVAL      { 0 }
    ::= { wwpLeosUserConfiguration 3 }

 wwpLeosUserPasswordMinimumNumericChars  OBJECT-TYPE
    SYNTAX      Unsigned32 (0..128)
    MAX-ACCESS  read-write
    STATUS      current
    DESCRIPTION "This object specifies the minimum number of numeric
                 characters that must be specified when setting the password
                 of a locally-authenticated user."
    DEFVAL      { 0 }
    ::= { wwpLeosUserConfiguration 4 }

 wwpLeosUserPasswordMinimumSpecialChars  OBJECT-TYPE
    SYNTAX      Unsigned32 (0..128)
    MAX-ACCESS  read-write
    STATUS      current
    DESCRIPTION "This object specifies the minimum number of special
                 characters (ASCII characters other than control and
                 alphanumeric, such as !@#$%^&*()) that must be specified when
                 setting the password of a locally-authenticated user."
    DEFVAL      { 0 }
    ::= { wwpLeosUserConfiguration 5 }

 wwpLeosUserPasswordMinimumChangeChars  OBJECT-TYPE
    SYNTAX      Unsigned32 (0..128)
    MAX-ACCESS  read-write
    STATUS      current
    DESCRIPTION "This object specifies the minimum number of characters by
                 which the new password must differ from the previous password
                 when setting the password of a locally-authenticated user."
    DEFVAL      { 0 }
    ::= { wwpLeosUserConfiguration 6 }

 wwpLeosUserPasswordMaximumRunLength  OBJECT-TYPE
    SYNTAX      Unsigned32 (0..128)
    MAX-ACCESS  read-write
    STATUS      current
    DESCRIPTION "This object specifies the maximum number of consecutive
                 occurrences (the run length) of the same character
                 (case-sensitive) that may be specified when setting the
                 password of a locally-authenticated user."
    DEFVAL      { 0 }
    ::= { wwpLeosUserConfiguration 7 }

 wwpLeosUserPasswordDisallowDictWords  OBJECT-TYPE
    SYNTAX      TruthValue
    MAX-ACCESS  read-write
    STATUS      current
    DESCRIPTION "This object specifies whether a password may contain a word
                 found in the dictionary when setting the password of a
                 locally-authenticated user."
    DEFVAL      { false }
    ::= { wwpLeosUserConfiguration 8 }

 wwpLeosUserPasswordDisallowUserName  OBJECT-TYPE
    SYNTAX      TruthValue
    MAX-ACCESS  read-write
    STATUS      current
    DESCRIPTION "This object specifies whether a password may contain the user
                 name or its reverse (case-insensitive) when setting the
                 password of a locally-authenticated user."
    DEFVAL      { false }
    ::= { wwpLeosUserConfiguration 9 }

 wwpLeosUserMinimumUsernameLength  OBJECT-TYPE
    SYNTAX      Unsigned32 (1..32)
    MAX-ACCESS  read-write
    STATUS      current
    DESCRIPTION "This object specifies the minimum number of characters that
                 must be specified when setting the username of a
                 locally-authenticated user."
    DEFVAL      { 1 }
    ::= { wwpLeosUserConfiguration 10 }


 wwpLeosUserFallbackAdminState  OBJECT-TYPE
    SYNTAX      INTEGER {
                           enabled(1),
                           disabled(2)
                        }
    MAX-ACCESS  read-write
    STATUS      current
    DESCRIPTION "This object provides a configuration knob that can be used to
                 override the default AAA authentication behavior for users
                 created locally and allow the authentication to fall back to
                 local authentication method when the remote authentication fails.
                 The user should exercise this option very cautiously."
    DEFVAL      { disabled }
    ::= { wwpLeosUserConfiguration 11 }

 END

 --
 -- WWP-User-MIB
 --
