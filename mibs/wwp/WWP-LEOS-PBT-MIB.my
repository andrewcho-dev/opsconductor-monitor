-- This file was included in WWP MIB release 04-21-05-0007
 --
 -- WWP-LEOS-PBT-MIB.my
 --
 --

 WWP-LEOS-PBT-MIB DEFINITIONS ::= BEGIN

 IMPORTS
   Integer32, Unsigned32, Counter32, OBJECT-TYPE, NOTIFICATION-TYPE, MODULE-IDENTITY
        FROM SNMPv2-SMI
   TruthValue, DisplayString, MacAddress, RowStatus
        FROM SNMPv2-TC
   OBJECT-GROUP, NOTIFICATION-GROUP
        FROM SNMPv2-CONF
   wwpLeosVplsEncapTunnelId, wwpLeosVplsEncapTunnelName, wwpLeosVplsEncapTunnelActive, wwpLeosVplsEncapTunnelBVID
            FROM WWP-LEOS-VPLS-MIB
   wwpModulesLeos
        FROM WWP-SMI;

 wwpLeosPbtMIB MODULE-IDENTITY
            LAST-UPDATED "201711150000Z"
            ORGANIZATION "Ciena Corp."
            CONTACT-INFO
                    "   Mib Meister
                        7035 Ridge Road
                        Hanover, Maryland 21076
                        USA
                        Phone:  +1 800 921 1144
                        Email:  support@ciena.com"
            DESCRIPTION
                    "Added objects wwpLeosPbtVirtualCircuitDestBridgeIndex, wwpLeosPbtTunnelSwitchOverHoldTime, WwpLeosTcePbtServiceEntry
                     wwpLeosPbtLocalBridgeNameMacMapEntry, wwpLeosTcePbtTnlGroupEntry, wwpLeosTcePbtEncapTnlEntry,
                     wwpLeosTcePbtDecapTnlEntry, wwpLeosTcePbtServiceUserFrameL2TransformEntry.
                     Added Notifications wwpLeosTcePbtTunnelActivateNotification, wwpLeosTcePbtTunnelDeactivateNotification,
                     wwpLeosTcePbtTunnelReversionNotification."

            REVISION     "201711150000Z"
            DESCRIPTION
                    "Updated contact info."
            REVISION    "201304290000Z"
            DESCRIPTION
                    "Miscellaneous spelling and description corrections."
            REVISION   "201107050000Z"
            DESCRIPTION
                    "Added wwpLeosPbtTransitTunnelEtypeRemark."
            REVISION    "201105051600Z"
            DESCRIPTION
                    "Deprecated object wwpLeosPbtTunnelFaultNotification."
            REVISION     "201101310000Z"
            DESCRIPTION
                    "Added wwpLeosPbtTunnelReversionState and wwpLeosPbtTunnelReversionHoldTime."
            REVISION    "200703021700Z"
            DESCRIPTION
                    "This MIB module defines the managed objects for the PBT
                     (Provider Backbone Transport) feature for LEOS based WWP products."
            REVISION    "200608251700Z"
            DESCRIPTION
                    "Initial creation."
            ::= { wwpModulesLeos 38 }

 --
 -- Node definitions
 --
 wwpLeosPbtMIBObjects OBJECT IDENTIFIER ::= { wwpLeosPbtMIB 1 }
 wwpLeosPbt           OBJECT IDENTIFIER ::= { wwpLeosPbtMIBObjects 1 } 
  
 -- Notifications   
 wwpLeosPbtMIBNotificationPrefix  OBJECT IDENTIFIER ::=  { wwpLeosPbtMIB 2 } 
 wwpLeosPbtMIBNotifications       OBJECT IDENTIFIER ::=  { wwpLeosPbtMIBNotificationPrefix 0 }

 -- Conformance information  
 wwpLeosPbtMIBConformance OBJECT IDENTIFIER ::= { wwpLeosPbtMIB 3 } 
 wwpLeosPbtMIBCompliances OBJECT IDENTIFIER ::= { wwpLeosPbtMIBConformance 1 }                
 wwpLeosPbtMIBGroups      OBJECT IDENTIFIER ::= { wwpLeosPbtMIBConformance 2 } 

 --
 -- PBT Global Attrs
 --                                                           
 wwpLeosPbtGlobalAttrs  OBJECT IDENTIFIER ::= { wwpLeosPbt 1 } 
 
 wwpLeosPbtBridgeMac OBJECT-TYPE
     SYNTAX      MacAddress
     MAX-ACCESS  read-write
     STATUS      current
     DESCRIPTION
        "This represents the provider MAC address to be used as source MAC during PBT encapsulation.
         If this object is not set then it returns default MAC derived from chassis MAC."
     ::= { wwpLeosPbtGlobalAttrs 1 }
 
 wwpLeosPbtServiceTagEType OBJECT-TYPE
     SYNTAX      OCTET STRING (SIZE(1..2))
     MAX-ACCESS  read-write
     STATUS      current
     DESCRIPTION
        "This represents the etype value to be used in I-Tag (Service tag) section of PBT encapsulation. 
        The I-tag ether type cannot be modified in native mode PBT"
     ::= { wwpLeosPbtGlobalAttrs 2 }
 
 wwpLeosPbtTunnelTagEtype OBJECT-TYPE
     SYNTAX      OCTET STRING (SIZE(1..2))
     MAX-ACCESS  read-write
     STATUS      current
     DESCRIPTION
        "This represents the etype value to be used in B-Tag section of PBT encapsulation. Valid values are
        8100, 9100 & 88a8"
     ::= { wwpLeosPbtGlobalAttrs 3 }                                     
                               
 wwpLeosPbtTunnelReversionState OBJECT-TYPE
     SYNTAX      INTEGER {
     				enabled(1),
     				disabled(2)
     			 }     			 
     MAX-ACCESS  read-write
     STATUS      current
     DESCRIPTION
        "Setting this object enables or disables automatic tunnel reversion from backup to primary
         if the primary becomes back up. The device waits for wwpLeosPbtTunnelReversionHoldTime before
	 automatically switching that data traffic back to primary."  
     DEFVAL     {disabled}
     ::= { wwpLeosPbtGlobalAttrs 4 } 
     
 wwpLeosPbtTunnelReversionHoldTime OBJECT-TYPE
     SYNTAX      Unsigned32
     UNITS       "milliseconds"
     MAX-ACCESS  read-write
     STATUS      current     
     DESCRIPTION
        "This object represents the hold time before data traffic on the backup tunnel automatically 
         reverts to the primary tunnel. "
     DEFVAL     {3000}     
     ::= { wwpLeosPbtGlobalAttrs 5 }

 wwpLeosPbtTransitTunnelEtypeRemark OBJECT-TYPE
      SYNTAX     INTEGER {
     				enabled(1),
     				disabled(2)
     			 }     			 
     MAX-ACCESS  read-write
     STATUS      current
     DESCRIPTION
        "Setting this object enables or disables remarking of the EtherType field in the B-Tag
         (tunnel) portion of PBT frames that are transiting through the device without PBT encapsulation,
         or decapsulation.  While enabled, applicable PBT transit frames egressing a PBT port
         have their B-Tag EtherType marked with the value configured as the wwpLeosPbtTunnelTagEtype."
     DEFVAL     {enabled}
     ::= { wwpLeosPbtGlobalAttrs 6 } 

wwpLeosPbtAdminMode OBJECT-TYPE
     SYNTAX     INTEGER {
    				nonNative(1),
     				native(2)
     			 }     			 
     MAX-ACCESS  read-write
     STATUS      current
     DESCRIPTION
        " This object represents PBT Admin mode. Some platforms support either non-native or native mode."
     ::= { wwpLeosPbtGlobalAttrs 7 } 
     
wwpLeosPbtOperMode OBJECT-TYPE
     SYNTAX     INTEGER {
    				nonNative(1),
     				native(2)
     			 }     			 
     MAX-ACCESS  read-write
     STATUS      current
     DESCRIPTION
        " This object represents PBT Oper mode. Some platforms support either non-native or native mode."
     ::= { wwpLeosPbtGlobalAttrs 8 }     
     
 wwpLeosPbtServiceVlanTpid OBJECT-TYPE
     SYNTAX      OCTET STRING (SIZE(1..2))
     MAX-ACCESS  read-write
     STATUS      current
     DESCRIPTION     
        "When operating in native mode, this is the value of the
        service VLAN TPID that is used if retain-stag is set to TRUE.
        This is configurable only in native mode PBT. In non-native
        mode, this value defaults to the 0x8100 and cannot be changed. Valid
        values are 8100, 9100 and 88a8"
     ::= { wwpLeosPbtGlobalAttrs 9 }  

 wwpLeosPbtTunnelSwitchOverHoldTime OBJECT-TYPE
     SYNTAX      Unsigned32
     UNITS       "milliseconds"
     MAX-ACCESS  read-write
     STATUS      current     
     DESCRIPTION
        "This object represents the hold time before data traffic on the backup tunnel automatically
         switches over to the primary tunnel."
     DEFVAL     {0}     
     ::= { wwpLeosPbtGlobalAttrs 10 }

 -- 
 -- add new tce attribute for reverseTime? Yes, to add in the reverse time.
 -- 
     
 --
 -- PBT host name to MAC table
 -- 
 wwpLeosPbtBridgeNameMacMapTable OBJECT-TYPE
     SYNTAX     SEQUENCE OF WwpLeosPbtBridgeNameMacMapEntry
     MAX-ACCESS not-accessible
     STATUS     current
     DESCRIPTION
            "The (conceptual) table listing the host names to MAC mapping table.
             To create entry in this table use SNMP multiple set operation.
             wwpLeosPbtBridgeNameMacMapBridgeName must be specified.
             wwpLeosPbtBridgeNameMacMapMacAddr must be specified.
             wwpLeosPbtBridgeNameMacMapRowStatus must be  specified."
     ::= { wwpLeosPbt 2 }
     
 wwpLeosPbtBridgeNameMacMapEntry  OBJECT-TYPE
     SYNTAX       WwpLeosPbtBridgeNameMacMapEntry
     MAX-ACCESS   not-accessible
     STATUS       current
     DESCRIPTION
             "The host name to MAC address table entry indexed by wwpLeosPbtBridgeNameMacMapIndex."
     INDEX { wwpLeosPbtBridgeNameMacMapIndex }
     ::= { wwpLeosPbtBridgeNameMacMapTable 1 }
     
 WwpLeosPbtBridgeNameMacMapEntry ::=  SEQUENCE {
     wwpLeosPbtBridgeNameMacMapIndex                     INTEGER,
     wwpLeosPbtBridgeNameMacMapBridgeName                  DisplayString,
     wwpLeosPbtBridgeNameMacMapMacAddr                   MacAddress,
     wwpLeosPbtBridgeNameMacMapUseCount				   Counter32,
     wwpLeosPbtBridgeNameMacMapRowStatus                 RowStatus
 }
 
 wwpLeosPbtBridgeNameMacMapIndex OBJECT-TYPE
     SYNTAX      INTEGER (1..64)
     MAX-ACCESS  read-only
     STATUS      current
     DESCRIPTION
        "This represents the unique index in the table."
     ::= { wwpLeosPbtBridgeNameMacMapEntry 1 }
  
 wwpLeosPbtBridgeNameMacMapBridgeName OBJECT-TYPE
     SYNTAX      DisplayString (SIZE (1..15))
     MAX-ACCESS  read-create
     STATUS      current
     DESCRIPTION
        "This represents the host name of the provider edge device.
         This object cannot be modified."
     ::= { wwpLeosPbtBridgeNameMacMapEntry 2 }
  
 wwpLeosPbtBridgeNameMacMapMacAddr OBJECT-TYPE
     SYNTAX      MacAddress
     MAX-ACCESS  read-create
     STATUS      current
     DESCRIPTION
        "This represents the MAC address of the provider edge device.
         This object cannot be modified."
     ::= { wwpLeosPbtBridgeNameMacMapEntry 3 }
 
 wwpLeosPbtBridgeNameMacMapUseCount OBJECT-TYPE
     SYNTAX      Counter32
     MAX-ACCESS  read-only
     STATUS      current
     DESCRIPTION
        "This object specifies the total number of encap tunnels using this entry."
     ::= { wwpLeosPbtBridgeNameMacMapEntry 4 }
     
 wwpLeosPbtBridgeNameMacMapRowStatus OBJECT-TYPE
     SYNTAX      RowStatus
     MAX-ACCESS  read-create
     STATUS      current
     DESCRIPTION
        "Setting this object to 'createAndGo' creates the entry	in the table.
         Setting this object to 'destroy' deletes the entry from the table."
     ::= { wwpLeosPbtBridgeNameMacMapEntry 5 }
 
  --
  -- BVID Reservation
  wwpLeosPbtReservedBVIDTable OBJECT-TYPE
     SYNTAX     SEQUENCE OF WwpLeosPbtReservedBVIDEntry
     MAX-ACCESS not-accessible
     STATUS     current
     DESCRIPTION
            "The (conceptual) table listing the BVIDs reserved for the provider backbone bridge tunnels."
     ::= { wwpLeosPbt 3 }
     
 wwpLeosPbtReservedBVIDEntry  OBJECT-TYPE
     SYNTAX       WwpLeosPbtReservedBVIDEntry
     MAX-ACCESS   not-accessible
     STATUS       current
     DESCRIPTION
             "The entry to reserve BVIDs for the provider backbone bridge tunnels."
     INDEX {wwpLeosPbtReservedBVID}
     ::= { wwpLeosPbtReservedBVIDTable 1 }
     
 WwpLeosPbtReservedBVIDEntry ::=  SEQUENCE { 
     wwpLeosPbtReservedBVID          Integer32,
     wwpLeosPbtReservedBVIDRowStatus    RowStatus
 }

 wwpLeosPbtReservedBVID OBJECT-TYPE
     SYNTAX      Integer32 (2..4094)
     MAX-ACCESS  read-only
     STATUS      current
     DESCRIPTION
        "This object is used to specify the VLAN ID to be reserved for PBT tunnels. "
     ::= { wwpLeosPbtReservedBVIDEntry 1 }

 wwpLeosPbtReservedBVIDRowStatus OBJECT-TYPE
     SYNTAX      RowStatus
     MAX-ACCESS  read-create
     STATUS      current
     DESCRIPTION
        "Setting this object to 'createandgo' reserves the BVID VLAN for provider backbone bridge tunnels.
         Setting this object to 'destroy means the BVID VLAN is no longer reserved for the virtual switch."
     ::= { wwpLeosPbtReservedBVIDEntry 2 }                              
 
 --
 -- Virtual circuit pbt table
 -- 
 wwpLeosPbtVirtualCircuitTable OBJECT-TYPE
     SYNTAX     SEQUENCE OF WwpLeosPbtVirtualCircuitEntry
     MAX-ACCESS not-accessible
     STATUS     current
     DESCRIPTION
            "The (conceptual) table listing the virtual circuit MAC in MAC table.
             To create entry use SNMP multiple set operation because the following objects 
             need to be set when creating an entry in the table.
             wwpLeosPbtVirtualCircuitName must be specified.             
             wwpLeosPbtVirtualCircuitIngressISID must be specified.
             wwpLeosPbtVirtualCircuitEgressISID must be specified.             
             wwpLeosPbtVirtualCircuitRowStatus must be specified.
             wwpLeosPbtVirtualCircuitIngressISID & wwpLeosPbtVirtualCircuitEgressISID must be the same values."
     ::= { wwpLeosPbt 4 }
     
 wwpLeosPbtVirtualCircuitEntry  OBJECT-TYPE
     SYNTAX       WwpLeosPbtVirtualCircuitEntry
     MAX-ACCESS   not-accessible
     STATUS       current
     DESCRIPTION
             "The virtual circuit table entry indexed by wwpLeosPbtVirtualCircuitIndex."
     INDEX { wwpLeosPbtVirtualCircuitIndex }
     ::= { wwpLeosPbtVirtualCircuitTable 1 }
     
 WwpLeosPbtVirtualCircuitEntry ::=  SEQUENCE {
     wwpLeosPbtVirtualCircuitIndex                         INTEGER,                
     wwpLeosPbtVirtualCircuitName                          DisplayString,     
     wwpLeosPbtVirtualCircuitFixedEncapTunnelId              Integer32,     
     wwpLeosPbtVirtualCircuitDestBridgeIndex               Integer32,     
     wwpLeosPbtVirtualCircuitIngressISID                   Integer32,
     wwpLeosPbtVirtualCircuitEgressISID                    Integer32,      
     wwpLeosPbtVirtualCircuitOperState					   INTEGER,
     wwpLeosPbtVirtualCircuitEncapTunnelIdInUse            Integer32,     
     wwpLeosPbtVirtualCircuitRowStatus                	   RowStatus,     
     wwpLeosPbtVirtualCircuitRetainSTAG                    TruthValue,
     wwpLeosPbtVirtualCircuitStag                          Integer32,
     wwpLeosPbtVirtualCircuitReplaceCTAG                   TruthValue,
     wwpLeosPbtVirtualCircuitCtag                          Integer32    
 }
 
 wwpLeosPbtVirtualCircuitIndex OBJECT-TYPE
     SYNTAX      INTEGER (1..65535)
     MAX-ACCESS  read-only
     STATUS      current
     DESCRIPTION
        "This represents the virtual circuit MAC in MAC index in the table.
         This number should be unique in the table."
     ::= { wwpLeosPbtVirtualCircuitEntry 1 }
 
 wwpLeosPbtVirtualCircuitName OBJECT-TYPE
     SYNTAX      DisplayString (SIZE (1..15))
     MAX-ACCESS  read-create
     STATUS      current
     DESCRIPTION
        "This represents the name of the MAC in MAC virtual circuit."
     ::= { wwpLeosPbtVirtualCircuitEntry 2 } 
 
 wwpLeosPbtVirtualCircuitFixedEncapTunnelId OBJECT-TYPE
     SYNTAX      Integer32 
     MAX-ACCESS  read-create
     STATUS      current
     DESCRIPTION
        "This represents the fixed tunnel this virtual circuit should be mapped to."
     ::= { wwpLeosPbtVirtualCircuitEntry 3 }     
   
 wwpLeosPbtVirtualCircuitDestBridgeIndex OBJECT-TYPE
     SYNTAX      Integer32 (0..64)
     MAX-ACCESS  read-create
     STATUS      current
     DESCRIPTION
        "This represents the provider destination host name used for this tunnel.
         This must be set to one of the value specified by wwpLeosPbtBridgeNameMacMapIndex.
         If set to 0, the device interprets it as not specified."
     ::= { wwpLeosPbtVirtualCircuitEntry 4 }
  
  wwpLeosPbtVirtualCircuitIngressISID OBJECT-TYPE
     SYNTAX      Integer32 (1..16777215)
     MAX-ACCESS  read-create
     STATUS      current
     DESCRIPTION
        "This represents the ingress ISID associated with the virtual circuit."
     ::= { wwpLeosPbtVirtualCircuitEntry 5 }
  
  wwpLeosPbtVirtualCircuitEgressISID OBJECT-TYPE
     SYNTAX      Integer32 (1..16777215)
     MAX-ACCESS  read-create
     STATUS      current
     DESCRIPTION
        "This represents the egress ISID associated with the virtual circuit."
     ::= { wwpLeosPbtVirtualCircuitEntry 6 }  
  
  wwpLeosPbtVirtualCircuitOperState OBJECT-TYPE
     SYNTAX      INTEGER {
     				disabled(1),
     				enabled(2)     				
     			}
     MAX-ACCESS  read-only
     STATUS      current
     DESCRIPTION
        "This represents the operational state of this virtual circuit."
     ::= { wwpLeosPbtVirtualCircuitEntry 7 }
  
  wwpLeosPbtVirtualCircuitEncapTunnelIdInUse OBJECT-TYPE
     SYNTAX      Integer32 
     MAX-ACCESS  read-only
     STATUS      current
     DESCRIPTION
        "This represents the tunnel ID of the active tunnel this virtual circuit is currently using. 
         This tunnel can be the primary or backup tunnel."
     ::= { wwpLeosPbtVirtualCircuitEntry 8 }

  wwpLeosPbtVirtualCircuitRowStatus OBJECT-TYPE
     SYNTAX      RowStatus
     MAX-ACCESS  read-create
     STATUS      current
     DESCRIPTION
        "Used to manage the creation and deletion of the conceptual rows in this table.
	To create a row in this table, set this object to 'createAndGo'.
	To delete a row in this table, set this object to 'destroy'.
	If the entry exists, it is displayed as 'active'."
     ::= { wwpLeosPbtVirtualCircuitEntry 9 }
   
  wwpLeosPbtVirtualCircuitRetainSTAG OBJECT-TYPE
     SYNTAX      TruthValue
     MAX-ACCESS  read-create
     STATUS      current
     DESCRIPTION
        "When operating in PBT mode, writing TRUE(1)
         to this object forces this VC to retain the S-Tag.
         When FALSE(0) is written, the S-Tag is popped
         on egress and the tag is pushed on ingress."
     ::= { wwpLeosPbtVirtualCircuitEntry 10 } 
     
  wwpLeosPbtVirtualCircuitStag OBJECT-TYPE
     SYNTAX      Integer32
     MAX-ACCESS  read-create
     STATUS      current
     DESCRIPTION
        "When operating in PBT mode, this is the value of the
        S-Tag that is used if wwpLeosPbtVirtualCircuitRetainSTAG is set to TRUE.
        This is configurable only in native mode PBT. In non-native
        mode, this value defaults to the RVID and cannot be changed."
     ::= { wwpLeosPbtVirtualCircuitEntry 11 }    
       
  wwpLeosPbtVirtualCircuitReplaceCTAG OBJECT-TYPE
     SYNTAX      TruthValue
     MAX-ACCESS  read-create
     STATUS      current
     DESCRIPTION
        "When operating in native mode PBT, setting this object to TRUE(1)
         replaces the C-Tag with the c-tag value configured.
         When set to FALSE(0)the C-Tag is unchanged. A valid non-zero
         C-Tag value has to be specified for wwpLeosPbtVirtualCircuitCtag when
         setting this object to TRUE(1)."         
     ::= { wwpLeosPbtVirtualCircuitEntry 12 } 
     
  wwpLeosPbtVirtualCircuitCtag OBJECT-TYPE
     SYNTAX      Integer32
     MAX-ACCESS  read-create
     STATUS      current
     DESCRIPTION
        "When operating in native mode PBT, this is the value of the
        C-Tag that is used if wwpLeosPbtVirtualCircuitReplaceCTAG is set to TRUE."        
     ::= { wwpLeosPbtVirtualCircuitEntry 13 }      
  
 --
 -- PBT VC stats
 wwpLeosPbtVirtualCircuitStatsTable OBJECT-TYPE
     SYNTAX     SEQUENCE OF WwpLeosPbtVirtualCircuitStatsEntry
     MAX-ACCESS not-accessible
     STATUS     current
     DESCRIPTION
            "The (conceptual) table listing the MPLS virtual circuit statistics
             table."
     ::= { wwpLeosPbt 5 }
    
 wwpLeosPbtVirtualCircuitStatsEntry  OBJECT-TYPE
     SYNTAX       WwpLeosPbtVirtualCircuitStatsEntry
     MAX-ACCESS   not-accessible
     STATUS       current
     DESCRIPTION
             "The MPLS virtual circuit statistics table entry indexed by
              wwpLeosPbtVirtualCircuitMplsIndex."
     INDEX { wwpLeosPbtVirtualCircuitIndex }
     ::= { wwpLeosPbtVirtualCircuitStatsTable 1 }
     
 WwpLeosPbtVirtualCircuitStatsEntry ::=  SEQUENCE {   
         wwpLeosPbtVirtualCircuitTxBytesHi Counter32,
         wwpLeosPbtVirtualCircuitTxBytesLo Counter32,    
         wwpLeosPbtVirtualCircuitRxBytesHi Counter32,
         wwpLeosPbtVirtualCircuitRxBytesLo Counter32
 }
 
 wwpLeosPbtVirtualCircuitTxBytesHi OBJECT-TYPE
     SYNTAX      Counter32
     MAX-ACCESS  read-only
     STATUS      current
     DESCRIPTION
        "This represents the total number of higher 32 bits transmitted for
         given virtual circuit."
     ::= { wwpLeosPbtVirtualCircuitStatsEntry 1 }
     
 wwpLeosPbtVirtualCircuitTxBytesLo OBJECT-TYPE
     SYNTAX      Counter32
     MAX-ACCESS  read-only
     STATUS      current
     DESCRIPTION
        "This represents the total number of lower 32 bits transmitted for
         given virtual circuit."
     ::= { wwpLeosPbtVirtualCircuitStatsEntry 2 }
      
 wwpLeosPbtVirtualCircuitRxBytesHi OBJECT-TYPE
     SYNTAX      Counter32
     MAX-ACCESS  read-only
     STATUS      current
     DESCRIPTION
        "This represents the total number of higher 32 bits received for
         given mpls virtual circuit."
     ::= { wwpLeosPbtVirtualCircuitStatsEntry 3 }
     
 wwpLeosPbtVirtualCircuitRxBytesLo OBJECT-TYPE
     SYNTAX      Counter32
     MAX-ACCESS  read-only
     STATUS      current
     DESCRIPTION
        "This represents the total number of lower 32 bits received for
         given virtual circuit."
     ::= { wwpLeosPbtVirtualCircuitStatsEntry 4 }  
     
     
 --
 -- Local Bridge
 --        
 
 wwpLeosPbtLocalBridgeNameMacMapTable OBJECT-TYPE
     SYNTAX     SEQUENCE OF WwpLeosPbtLocalBridgeNameMacMapEntry
     MAX-ACCESS not-accessible
     STATUS     current
     DESCRIPTION
            "The (conceptual) table listing the host names to MAC mapping table.
             To create entry in this table use SNMP multiple set operation.
             wwpLeosPbtHostNameMacMapHostName must be specified.
             wwpLeosPbtHostNameMacMapMacAddr must be specified.
             wwpLeosPbtHostNameMacMapRowStatus must be specified."
     ::= { wwpLeosPbt 6 }
     
 wwpLeosPbtLocalBridgeNameMacMapEntry  OBJECT-TYPE
     SYNTAX       WwpLeosPbtLocalBridgeNameMacMapEntry
     MAX-ACCESS   not-accessible
     STATUS       current
     DESCRIPTION
             "The host name to MAC address table entry indexed by wwpLeosPbtLocalBridgeNameMacMapIndex."
     INDEX { wwpLeosPbtLocalBridgeNameMacMapIndex }
     ::= { wwpLeosPbtLocalBridgeNameMacMapTable 1 }
     
 WwpLeosPbtLocalBridgeNameMacMapEntry ::=  SEQUENCE {
     wwpLeosPbtLocalBridgeNameMacMapIndex                     INTEGER,
     wwpLeosPbtLocalBridgeNameMacMapBridgeName                  DisplayString,
     wwpLeosPbtLocalBridgeNameMacMapMacAddr                   MacAddress,
     wwpLeosPbtLocalBridgeNameMacMapUseCount				   Counter32,
     wwpLeosPbtLocalBridgeNameMacMapRowStatus                 RowStatus
 }
 
 wwpLeosPbtLocalBridgeNameMacMapIndex OBJECT-TYPE
     SYNTAX      INTEGER (1..64)
     MAX-ACCESS  read-only
     STATUS      current
     DESCRIPTION
        "This represents the unique index in the table."
     ::= { wwpLeosPbtLocalBridgeNameMacMapEntry 1 }
  
 wwpLeosPbtLocalBridgeNameMacMapBridgeName OBJECT-TYPE
     SYNTAX      DisplayString (SIZE (1..15))
     MAX-ACCESS  read-create
     STATUS      current
     DESCRIPTION
        "This represents the host name of the provider edge device.
         This object cannot be modified."
     ::= { wwpLeosPbtLocalBridgeNameMacMapEntry 2 }
  
 wwpLeosPbtLocalBridgeNameMacMapMacAddr OBJECT-TYPE
     SYNTAX      MacAddress
     MAX-ACCESS  read-only
     STATUS      current
     DESCRIPTION
        "This represents the MAC address of the provider edge device.
         This object cannot be modified."
     ::= { wwpLeosPbtLocalBridgeNameMacMapEntry 3 }
 
 wwpLeosPbtLocalBridgeNameMacMapUseCount OBJECT-TYPE
     SYNTAX      Counter32
     MAX-ACCESS  read-only
     STATUS      current
     DESCRIPTION
        "This object specifies the total number of encap tunnels using this entry."
     ::= { wwpLeosPbtLocalBridgeNameMacMapEntry 4 }
     
 wwpLeosPbtLocalBridgeNameMacMapRowStatus OBJECT-TYPE
     SYNTAX      RowStatus
     MAX-ACCESS  read-create
     STATUS      current
     DESCRIPTION
        "Setting this object to 'createAndGo' creates the entry	in the table.  
         Setting this object to 'destroy' deletes the entry from the table."
     ::= { wwpLeosPbtLocalBridgeNameMacMapEntry 5 }

 --
 -- TCE PBT 
 --
 wwpLeosTcePbt        OBJECT IDENTIFIER ::= { wwpLeosPbt 10 } 
 
 --
 -- TCE PBT service table
 --
 wwpLeosTcePbtServiceTable OBJECT-TYPE
     SYNTAX     SEQUENCE OF WwpLeosTcePbtServiceEntry
     MAX-ACCESS not-accessible
     STATUS     current
     DESCRIPTION
            "The (conceptual) table listing the PBT Service table.
             To create entry in this table use SNMP multiple set operation.
             wwpLeosTcePbtServiceName must be specified.
             wwpLeosTcePbtServiceIngressIsId must be specified.
             wwpLeosTcePbtServiceEgressIsId must be specified.
             wwpLeosTcePbtServiceRowStatus must be specified."
     ::= { wwpLeosTcePbt 1 }
     
 wwpLeosTcePbtServiceEntry  OBJECT-TYPE
     SYNTAX       WwpLeosTcePbtServiceEntry
     MAX-ACCESS   not-accessible
     STATUS       current
     DESCRIPTION
             "The PBT Service table entry indexed by wwpLeosTcePbtServiceIndex."
     INDEX { wwpLeosTcePbtServiceIndex }
     ::= { wwpLeosTcePbtServiceTable 1 }
     
 WwpLeosTcePbtServiceEntry ::=  SEQUENCE {
     wwpLeosTcePbtServiceIndex                     Unsigned32,
     wwpLeosTcePbtServiceName                      DisplayString,
     wwpLeosTcePbtServiceOperStatus                INTEGER,
     wwpLeosTcePbtServiceFloodContProfileId        INTEGER,
     wwpLeosTcePbtServiceFloodContProfileName      DisplayString,
     wwpLeosTcePbtServiceVsIndex                   Unsigned32,
     wwpLeosTcePbtServiceVsName                    DisplayString,
     wwpLeosTcePbtServiceTnlGroupIndex             Unsigned32,
     wwpLeosTcePbtServiceTnlGroupName              DisplayString,
     wwpLeosTcePbtServiceIngressIsId               Unsigned32,
     wwpLeosTcePbtServiceEgressIsId                Unsigned32,
     wwpLeosTcePbtServiceFixedEgressPcp            INTEGER,
     wwpLeosTcePbtServiceFrameCosPolicy            INTEGER,
     wwpLeosTcePbtServiceFrameCosMapIndex          INTEGER,
     wwpLeosTcePbtServiceFrameCosMapName           DisplayString,
     wwpLeosTcePbtServiceResolvedCosPolicy         INTEGER,
     wwpLeosTcePbtServiceResolvedCosProfileIndex   INTEGER,
     wwpLeosTcePbtServiceResolvedCosProfileName    DisplayString, 
     wwpLeosTcePbtServiceIngressMeterProfileId	   INTEGER,
     wwpLeosTcePbtServiceIngressMeterProfileName   DisplayString,
     wwpLeosTcePbtServiceIngressMeterPolicy	   INTEGER,
     wwpLeosTcePbtServiceRowStatus                 RowStatus
 }
 
 wwpLeosTcePbtServiceIndex OBJECT-TYPE
     SYNTAX      Unsigned32
     MAX-ACCESS  not-accessible
     STATUS      current
     DESCRIPTION
        "This represents the unique index in the table."
     ::= { wwpLeosTcePbtServiceEntry 1 }
  
 wwpLeosTcePbtServiceName OBJECT-TYPE
     SYNTAX      DisplayString (SIZE (1..31))
     MAX-ACCESS  read-create
     STATUS      current
     DESCRIPTION
        "This represents the PBT service name. This object cannot be modified."
     ::= { wwpLeosTcePbtServiceEntry 2 }
  
  wwpLeosTcePbtServiceOperStatus OBJECT-TYPE
     SYNTAX      INTEGER {
                     disabled(1),
                     enabled(2)                 
                 }
     MAX-ACCESS  read-only
     STATUS      current
     DESCRIPTION
        "This represents the operational state of this service."
     ::= { wwpLeosTcePbtServiceEntry 3 }
    
 wwpLeosTcePbtServiceFloodContProfileId OBJECT-TYPE
     SYNTAX      INTEGER (0..65535)
     MAX-ACCESS  read-create
     STATUS      current
     DESCRIPTION
        "PBT service ingress flood container profile index."
     ::= { wwpLeosTcePbtServiceEntry 4 }
  
 wwpLeosTcePbtServiceFloodContProfileName OBJECT-TYPE
     SYNTAX      DisplayString (SIZE (0..31))
     MAX-ACCESS  read-only
     STATUS      current
     DESCRIPTION
        "PBT service ingress flood container profile name."
     ::= { wwpLeosTcePbtServiceEntry 5 }
  
 wwpLeosTcePbtServiceVsIndex OBJECT-TYPE
     SYNTAX      Unsigned32
     MAX-ACCESS  read-create
     STATUS      current
     DESCRIPTION
        "Virtual switch index to which the PBT service is attached. To detach PBT service from the virtual switch, set this object to 0."
     ::= { wwpLeosTcePbtServiceEntry 6 }
  
 wwpLeosTcePbtServiceVsName OBJECT-TYPE
     SYNTAX      DisplayString (SIZE (0..31))
     MAX-ACCESS  read-only
     STATUS      current
     DESCRIPTION
        "Virtual switch name to which PBT service is attached."
     ::= { wwpLeosTcePbtServiceEntry 7 }
  
 wwpLeosTcePbtServiceTnlGroupIndex OBJECT-TYPE
     SYNTAX      Unsigned32
     MAX-ACCESS  read-create
     STATUS      current
     DESCRIPTION
        "PBT service tunnel group index."
     ::= { wwpLeosTcePbtServiceEntry 8 }
  
 wwpLeosTcePbtServiceTnlGroupName OBJECT-TYPE
     SYNTAX      DisplayString (SIZE (1..31))
     MAX-ACCESS  read-only
     STATUS      current
     DESCRIPTION
        "PBT service tunnel group name."
     ::= { wwpLeosTcePbtServiceEntry 9 }
  
 wwpLeosTcePbtServiceIngressIsId OBJECT-TYPE
     SYNTAX      Unsigned32
     MAX-ACCESS  read-create
     STATUS      current
     DESCRIPTION
        "PBT service ingress ISID."
     ::= { wwpLeosTcePbtServiceEntry 10 }
  
 wwpLeosTcePbtServiceEgressIsId OBJECT-TYPE
     SYNTAX      Unsigned32
     MAX-ACCESS  read-create
     STATUS      current
     DESCRIPTION
        "PBT service egress ISID."
     ::= { wwpLeosTcePbtServiceEntry 11 }
  
 wwpLeosTcePbtServiceFixedEgressPcp OBJECT-TYPE
     SYNTAX      INTEGER (0..15)
     MAX-ACCESS  read-create
     STATUS      current
     DESCRIPTION
        "PBT service fixed egress PCP."
     DEFVAL     {2}
     ::= { wwpLeosTcePbtServiceEntry 12 }
  
 wwpLeosTcePbtServiceFrameCosPolicy OBJECT-TYPE
     SYNTAX      INTEGER {
                     fixed(1),
                     isidPcPMap(2)
                 }
     MAX-ACCESS  read-create
     STATUS      current
     DESCRIPTION
        "PBT service frame CoS policy."
     DEFVAL     {isidPcPMap}
     ::= { wwpLeosTcePbtServiceEntry 13 }
  
 wwpLeosTcePbtServiceFrameCosMapIndex OBJECT-TYPE
     SYNTAX      INTEGER (0..65535)
     MAX-ACCESS  read-create
     STATUS      current
     DESCRIPTION
        "PBT service frame CoS map index."
     DEFVAL     {1}
     ::= { wwpLeosTcePbtServiceEntry 14 }
  
 wwpLeosTcePbtServiceFrameCosMapName OBJECT-TYPE
     SYNTAX      DisplayString (SIZE (0..31))
     MAX-ACCESS  read-only
     STATUS      current
     DESCRIPTION
        "PBT service frame CoS map name."
     ::= { wwpLeosTcePbtServiceEntry 15 }
  
 wwpLeosTcePbtServiceResolvedCosPolicy OBJECT-TYPE
     SYNTAX      INTEGER {
                        ignore(1),
                        fixed(2),
                        isidPcpMap(3)
                 }
     MAX-ACCESS  read-create
     STATUS      current
     DESCRIPTION
        "PBT service resolved CoS policy."
     DEFVAL     {isidPcpMap}
     ::= { wwpLeosTcePbtServiceEntry 16 }
  
 wwpLeosTcePbtServiceResolvedCosProfileIndex OBJECT-TYPE
     SYNTAX      INTEGER (0..65535)
     MAX-ACCESS  read-create
     STATUS      current
     DESCRIPTION
        "PBT service resolved CoS profile index."
     DEFVAL     {1}
     ::= { wwpLeosTcePbtServiceEntry 17 }
  
 wwpLeosTcePbtServiceResolvedCosProfileName OBJECT-TYPE
     SYNTAX      DisplayString (SIZE (0..31))
     MAX-ACCESS  read-only
     STATUS      current
     DESCRIPTION
        "PBT service resolved CoS profile name."
     ::= { wwpLeosTcePbtServiceEntry 18 }   
  
 wwpLeosTcePbtServiceIngressMeterProfileId OBJECT-TYPE
 	SYNTAX   INTEGER  (0..65535)
 	MAX-ACCESS read-create
 	STATUS current
 	DESCRIPTION
 		"Ingress meter profile ID."
 	::= {wwpLeosTcePbtServiceEntry 19 }
 
 wwpLeosTcePbtServiceIngressMeterProfileName OBJECT-TYPE
 	SYNTAX DisplayString
 	MAX-ACCESS read-only
 	STATUS current
 	DESCRIPTION 
 		"Ingress meter profile name."
 	::= {wwpLeosTcePbtServiceEntry 20} 

 wwpLeosTcePbtServiceIngressMeterPolicy OBJECT-TYPE
 	SYNTAX INTEGER {
 			nonhierarchical(1),
 			hierarchical(2)
 			}
 	MAX-ACCESS read-only
 	STATUS current
 	DESCRIPTION 
 			"Ingress meter policy."
 	::= { wwpLeosTcePbtServiceEntry 21}			
 			
  
 wwpLeosTcePbtServiceRowStatus OBJECT-TYPE
     SYNTAX      RowStatus
     MAX-ACCESS  read-create
     STATUS      current
     DESCRIPTION
        "Setting this object to 'createAndGo' creates the entry	in the table.
         Setting this object to 'destroy' deletes the entry from the table."
     ::= { wwpLeosTcePbtServiceEntry 64 }

   
 --
 -- PBT tunnel group table. Look at LE-OS MPLS MIB for commonalities. Look 
 -- encap and decap tunnel table. 
 -- keep new table in leos file
 -- 
 wwpLeosTcePbtTnlGroupTable OBJECT-TYPE
     SYNTAX     SEQUENCE OF WwpLeosTcePbtTnlGroupEntry
     MAX-ACCESS not-accessible
     STATUS     current
     DESCRIPTION
            "The (conceptual) table listing the PBT tunnel group table.
             To create entry in this table use SNMP multiple set operation.
             wwpLeosTcePbtTnlGroupName must be specified.
             wwpLeosTcePbtTnlGroupRowStatus must be specified."
     ::= { wwpLeosTcePbt 5 }
     
 wwpLeosTcePbtTnlGroupEntry  OBJECT-TYPE
     SYNTAX       WwpLeosTcePbtTnlGroupEntry
     MAX-ACCESS   not-accessible
     STATUS       current
     DESCRIPTION
             "This represents an entry in the PBT tunnel group table."
     INDEX { wwpLeosTcePbtTnlGroupIndex }
     ::= { wwpLeosTcePbtTnlGroupTable 1 }
     
 WwpLeosTcePbtTnlGroupEntry ::=  SEQUENCE {
     wwpLeosTcePbtTnlGroupIndex                    Unsigned32,
     wwpLeosTcePbtTnlGroupName                     DisplayString,
     wwpLeosTcePbtTnlGroupSyncEnabled              TruthValue,
     wwpLeosTcePbtTnlGroupOperStatus               INTEGER,
     wwpLeosTcePbtTnlGroupUseCount                 Unsigned32,
     wwpLeosTcePbtTnlGroupActivePair               Unsigned32,
     wwpLeosTcePbtTnlGroupReverting                TruthValue,
     wwpLeosTcePbtTnlGroupRowStatus                RowStatus
 }

 wwpLeosTcePbtTnlGroupIndex OBJECT-TYPE
     SYNTAX      Unsigned32
     MAX-ACCESS  accessible-for-notify
     STATUS      current
     DESCRIPTION
        "This represents the unique index in the table."
     ::= { wwpLeosTcePbtTnlGroupEntry 1 }
  
 wwpLeosTcePbtTnlGroupName OBJECT-TYPE
     SYNTAX      DisplayString (SIZE (1..31))
     MAX-ACCESS  read-create
     STATUS      current
     DESCRIPTION
        "This represents the tunnel group name. This object cannot be modified."
     ::= { wwpLeosTcePbtTnlGroupEntry 2 }
  
  wwpLeosTcePbtTnlGroupSyncEnabled OBJECT-TYPE
     SYNTAX      TruthValue
     MAX-ACCESS  read-create
     STATUS      current
     DESCRIPTION
        "This object specifies if the tunnel group sync is enabled."
     DEFVAL     { false }
     ::= { wwpLeosTcePbtTnlGroupEntry 3 }
  
  wwpLeosTcePbtTnlGroupOperStatus OBJECT-TYPE
     SYNTAX      INTEGER {
                     disabled(1),
                     enabled(2)                 
                 }
     MAX-ACCESS  read-only
     STATUS      current
     DESCRIPTION
        "This represents the operational state of this service."
     ::= { wwpLeosTcePbtTnlGroupEntry 4 }
  
 wwpLeosTcePbtTnlGroupUseCount OBJECT-TYPE
     SYNTAX      Unsigned32
     MAX-ACCESS  read-only
     STATUS      current
     DESCRIPTION
        "This object specifies the tunnel group use count."
     ::= { wwpLeosTcePbtTnlGroupEntry 5 }

 wwpLeosTcePbtTnlGroupActivePair OBJECT-TYPE
     SYNTAX      Unsigned32
     MAX-ACCESS  read-only
     STATUS      current
     DESCRIPTION
        "An active PBT tunnel pair is two bidirectional tunnels, one inbound and 
		 the other outbound, between the same pair of devices paired together
		 to represent a bidirectional PBT trunk. An inbound and an outbound 
		 tunnel must map to the same physical port of the device to qualify
		 for the pairing. "
     ::= { wwpLeosTcePbtTnlGroupEntry 6 }

 wwpLeosTcePbtTnlGroupReverting OBJECT-TYPE
     SYNTAX      TruthValue
     MAX-ACCESS  read-only
     STATUS      current
     DESCRIPTION
        "This object specifies the tunnel group revert option."
     ::= { wwpLeosTcePbtTnlGroupEntry 7}

 wwpLeosTcePbtTnlGroupRowStatus OBJECT-TYPE
     SYNTAX      RowStatus
     MAX-ACCESS  read-create
     STATUS      current
     DESCRIPTION
        "Setting this object to 'createAndGo' creates the entry in the table.
	Setting this object to 'destroy' deletes the entry from the table."
     ::= { wwpLeosTcePbtTnlGroupEntry 64 }
     

 --
 -- PBT Encap tunnel table
 --

 wwpLeosTcePbtEncapTnlTable OBJECT-TYPE
     SYNTAX     SEQUENCE OF WwpLeosTcePbtEncapTnlEntry
     MAX-ACCESS not-accessible
     STATUS     current
     DESCRIPTION
            "The (conceptual) table listing the PBT encap tunnels.
             To create entry in this table use SNMP multiple set operation.
             wwpLeosTcePbtEncapTnlName must be specified.
             wwpLeosTcePbtEncapTnlRemoteBridgeIndex must be specified.
             wwpLeosTcePbtEncapTnlBvId must be specified.
             wwpLeosTcePbtEncapTnlPgId must be specified.
             wwpLeosTcePbtEncapTnlRowStatus must be specified."

     ::= { wwpLeosTcePbt 6 }
     
 wwpLeosTcePbtEncapTnlEntry  OBJECT-TYPE
     SYNTAX       WwpLeosTcePbtEncapTnlEntry
     MAX-ACCESS   not-accessible
     STATUS       current
     DESCRIPTION
           "An entry (conceptual row) in the wwpLeosPbtEncapTnlTable."
     INDEX {wwpLeosTcePbtEncapTnlIndex}
     ::= { wwpLeosTcePbtEncapTnlTable 1 }
     
 WwpLeosTcePbtEncapTnlEntry ::=  SEQUENCE { 
     wwpLeosTcePbtEncapTnlIndex                 Unsigned32,
     wwpLeosTcePbtEncapTnlName                  DisplayString,
     wwpLeosTcePbtEncapTnlRemoteBridgeIndex     Unsigned32,
     wwpLeosTcePbtEncapTnlRemoteBridgeName      DisplayString,
     wwpLeosTcePbtEncapTnlGroupIndex            Unsigned32,
     wwpLeosTcePbtEncapTnlGroupName             DisplayString,
     wwpLeosTcePbtEncapTnlBvId                  Unsigned32,
     wwpLeosTcePbtEncapTnlPgId                  Unsigned32,
     wwpLeosTcePbtEncapTnlPortName              DisplayString,
     wwpLeosTcePbtEncapTnlFaults                Unsigned32,
     wwpLeosTcePbtEncapTnlAdminState            INTEGER,
     wwpLeosTcePbtEncapTnlOperState             INTEGER,
     wwpLeosTcePbtEncapTnlFwdState              INTEGER,
     wwpLeosTcePbtEncapTnlPaired                TruthValue,
     wwpLeosTcePbtEncapTnlPairIndex             INTEGER,
     wwpLeosTcePbtEncapTnlPairOperState         INTEGER,
     wwpLeosTcePbtEncapTnlFrameCosPolicy        INTEGER,
     wwpLeosTcePbtEncapTnlFrameCosMapIndex      Unsigned32,
     wwpLeosTcePbtEncapTnlFrameCosMapName       DisplayString,
     wwpLeosTcePbtEncapTnlFixedPcp              INTEGER,
     wwpLeosTcePbtEncapTnlCfmConfigured         TruthValue,
     wwpLeosTcePbtEncapTnlPairedDecapIndex      Unsigned32,
     wwpLeosTcePbtEncapTnlPairedDecapName       DisplayString,
     wwpLeosTcePbtEncapTnlWeight                Unsigned32,
     wwpLeosTcePbtEncapTnlStatsEnabled          TruthValue,
     wwpLeosTcePbtEncapTnlLocalBridgeIndex      Unsigned32,
     wwpLeosTcePbtEncapTnlLocalBridgeName       DisplayString,
     wwpLeosTcePbtEncapTnlReversionToPairIndex    Unsigned32,
     wwpLeosTcePbtEncapTnlReversionFromPairIndex    Unsigned32,
     wwpLeosTcePbtEncapTnlRowStatus             RowStatus
   }

 wwpLeosTcePbtEncapTnlIndex OBJECT-TYPE
     SYNTAX      Unsigned32
     MAX-ACCESS  accessible-for-notify
     STATUS      current
     DESCRIPTION
        "This represents the unique index in the table."
     ::= { wwpLeosTcePbtEncapTnlEntry 1 }
  
 wwpLeosTcePbtEncapTnlName OBJECT-TYPE
     SYNTAX      DisplayString (SIZE (1..31))
     MAX-ACCESS  read-create
     STATUS      current
     DESCRIPTION
        "This represents the encap tunnel name. This object cannot be modified."
     ::= { wwpLeosTcePbtEncapTnlEntry 2 }
  
 wwpLeosTcePbtEncapTnlRemoteBridgeIndex OBJECT-TYPE
     SYNTAX      Unsigned32
     MAX-ACCESS  read-create
     STATUS      current
     DESCRIPTION
        "This object represents the PBT encap tunnel remote bridge index."
     ::= { wwpLeosTcePbtEncapTnlEntry 3 }
  
 wwpLeosTcePbtEncapTnlRemoteBridgeName OBJECT-TYPE
     SYNTAX      DisplayString (SIZE (1..31))
     MAX-ACCESS  read-only
     STATUS      current
     DESCRIPTION
        "This object represents the PBT encap tunnel remote bridge name."
     ::= { wwpLeosTcePbtEncapTnlEntry 4 }
  
 wwpLeosTcePbtEncapTnlGroupIndex OBJECT-TYPE
     SYNTAX      Unsigned32
     MAX-ACCESS  read-create
     STATUS      current
     DESCRIPTION
        "This object represents the PBT encap tunnel group index."
     ::= { wwpLeosTcePbtEncapTnlEntry 5 }
  
 wwpLeosTcePbtEncapTnlGroupName OBJECT-TYPE
     SYNTAX      DisplayString (SIZE (1..31))
     MAX-ACCESS  read-only
     STATUS      current
     DESCRIPTION
        "This object represents the PBT encap tunnel group name."
     ::= { wwpLeosTcePbtEncapTnlEntry 6 }
  
 wwpLeosTcePbtEncapTnlBvId OBJECT-TYPE
     SYNTAX      Unsigned32
     MAX-ACCESS  read-create
     STATUS      current
     DESCRIPTION
        "This object represents the PBT encap tunnel BVID."
     ::= { wwpLeosTcePbtEncapTnlEntry 7 }
  
 wwpLeosTcePbtEncapTnlPgId OBJECT-TYPE
     SYNTAX      Unsigned32
     MAX-ACCESS  read-create
     STATUS      current
     DESCRIPTION
        "This object represents the PBT encap tunnel port."
     ::= { wwpLeosTcePbtEncapTnlEntry 8 }
  
 wwpLeosTcePbtEncapTnlPortName OBJECT-TYPE
     SYNTAX      DisplayString (SIZE (1..31))
     MAX-ACCESS  read-only
     STATUS      current
     DESCRIPTION
        "This object represents the PBT encap tunnel port name."
     ::= { wwpLeosTcePbtEncapTnlEntry 9 }
  

 wwpLeosTcePbtEncapTnlFaults OBJECT-TYPE
     SYNTAX      Unsigned32
     MAX-ACCESS  read-only
     STATUS      current
     DESCRIPTION
        "Each Bit Represents a fault. Value 0 represents no fault. First LSB represents port Fault. 
        Second LSB represents CFM fault and third LSB represent Admin Fault."
     ::= { wwpLeosTcePbtEncapTnlEntry 10 }
  
 wwpLeosTcePbtEncapTnlAdminState OBJECT-TYPE
     SYNTAX      INTEGER {
                     enabled(1),
                     disabled(2)
                 }
     MAX-ACCESS  read-create
     STATUS      current
     DESCRIPTION
        "This object represents the PBT encap tunnel administrative state."
     ::= { wwpLeosTcePbtEncapTnlEntry 11 }
  
 wwpLeosTcePbtEncapTnlOperState OBJECT-TYPE
     SYNTAX      INTEGER {
                     enabled(1),
                     disabled(2)
                 }
     MAX-ACCESS  read-only
     STATUS      current
     DESCRIPTION
        "This object represents the PBT encap tunnel operational state."
     ::= { wwpLeosTcePbtEncapTnlEntry 12 }
  
 wwpLeosTcePbtEncapTnlFwdState OBJECT-TYPE
     SYNTAX      INTEGER {
                    active(1),
                    standby(2)
                 }
     MAX-ACCESS  read-only
     STATUS      current
     DESCRIPTION
        "This object represents the PBT encap tunnel forwarding state."
     ::= { wwpLeosTcePbtEncapTnlEntry 13 }
  
 wwpLeosTcePbtEncapTnlPaired OBJECT-TYPE
     SYNTAX      TruthValue
     MAX-ACCESS  read-only
     STATUS      current
     DESCRIPTION
        "This object represents the PBT encap tunnel paired state."
     ::= { wwpLeosTcePbtEncapTnlEntry 14 }
  
 wwpLeosTcePbtEncapTnlPairIndex OBJECT-TYPE
     SYNTAX      INTEGER (0..7)
     MAX-ACCESS  read-create
     STATUS      current
     DESCRIPTION
        "This object represents the PBT encap tunnel paired index."
     ::= { wwpLeosTcePbtEncapTnlEntry 15 }

 wwpLeosTcePbtEncapTnlPairOperState OBJECT-TYPE
     SYNTAX      INTEGER {
                     enabled(1),
                     disabled(2)
                 }
     MAX-ACCESS  read-only
     STATUS      current
     DESCRIPTION
        "This object represents the PBT encap tunnel paired operational state."
     ::= { wwpLeosTcePbtEncapTnlEntry 16 }
  
 wwpLeosTcePbtEncapTnlFrameCosPolicy OBJECT-TYPE
     SYNTAX      INTEGER {
                     fixed(1),
                     isidPcPMap(2)
                 }
     MAX-ACCESS  read-create
     STATUS      current
     DESCRIPTION
        "This object represents the PBT encap tunnel frame CoS policy."
     ::= { wwpLeosTcePbtEncapTnlEntry 17 }
  
 wwpLeosTcePbtEncapTnlFrameCosMapIndex OBJECT-TYPE
     SYNTAX      Unsigned32
     MAX-ACCESS  read-create
     STATUS      current
     DESCRIPTION
        "This object represents the PBT encap tunnel CoS map index."
     ::= { wwpLeosTcePbtEncapTnlEntry 18 }
  
 wwpLeosTcePbtEncapTnlFrameCosMapName OBJECT-TYPE
     SYNTAX      DisplayString (SIZE (0..31))
     MAX-ACCESS  read-only
     STATUS      current
     DESCRIPTION
        "This object represents the PBT encap tunnel frame CoS map name. "
     ::= { wwpLeosTcePbtEncapTnlEntry 19 }
  
 wwpLeosTcePbtEncapTnlFixedPcp OBJECT-TYPE
     SYNTAX      INTEGER (1..65535)
     MAX-ACCESS  read-create
     STATUS      current
     DESCRIPTION
        "This object represents the PBT encap tunnel fixed PCP."
     ::= { wwpLeosTcePbtEncapTnlEntry 20 }
  
 wwpLeosTcePbtEncapTnlCfmConfigured OBJECT-TYPE
     SYNTAX      TruthValue
     MAX-ACCESS  read-only
     STATUS      current
     DESCRIPTION
        "This object indicates whether the PBT encap tunnel has CFM configured."
     ::= { wwpLeosTcePbtEncapTnlEntry 21 }
  
 wwpLeosTcePbtEncapTnlPairedDecapIndex OBJECT-TYPE
     SYNTAX      Unsigned32
     MAX-ACCESS  read-only
     STATUS      current
     DESCRIPTION
        "This object represents the PBT encap tunnel paired decap index."
     ::= { wwpLeosTcePbtEncapTnlEntry 22 }

 wwpLeosTcePbtEncapTnlPairedDecapName OBJECT-TYPE
     SYNTAX      DisplayString (SIZE (0..31))
     MAX-ACCESS  read-only
     STATUS      current
     DESCRIPTION
        "This object represents the PBT encap tunnel paired decap name."
     ::= { wwpLeosTcePbtEncapTnlEntry 23 }
  
 wwpLeosTcePbtEncapTnlWeight OBJECT-TYPE
     SYNTAX      Unsigned32
     MAX-ACCESS  read-create
     STATUS      current
     DESCRIPTION
        "This object represents the PBT encap tunnel weight."
     ::= { wwpLeosTcePbtEncapTnlEntry 24 }
  
 wwpLeosTcePbtEncapTnlStatsEnabled OBJECT-TYPE
     SYNTAX      TruthValue
     MAX-ACCESS  read-only
     STATUS      current
     DESCRIPTION
        "This object indicates whether the PBT encap tunnel has statistics enabled. "
     ::= { wwpLeosTcePbtEncapTnlEntry 25 }  
 
 wwpLeosTcePbtEncapTnlLocalBridgeIndex     OBJECT-TYPE
 	 SYNTAX Unsigned32
 	 MAX-ACCESS read-create
 	 STATUS current
 	 DESCRIPTION
 	 	" "
 	 ::= {wwpLeosTcePbtEncapTnlEntry 26 }
 
 wwpLeosTcePbtEncapTnlLocalBridgeName      OBJECT-TYPE
   SYNTAX DisplayString
   MAX-ACCESS read-only
   STATUS current
   DESCRIPTION
   	"This object represents the PBT encap tunnel local bridge name."
   ::= { wwpLeosTcePbtEncapTnlEntry 27 }
     
  wwpLeosTcePbtEncapTnlReversionToPairIndex OBJECT-TYPE
     SYNTAX      Unsigned32
     MAX-ACCESS  accessible-for-notify
     STATUS      current
     DESCRIPTION
        "Reversion occurs to this tunnel pair index in a tunnel group
        and is used in the definition of trap.."
     ::= { wwpLeosTcePbtEncapTnlEntry 28 }   

 wwpLeosTcePbtEncapTnlReversionFromPairIndex OBJECT-TYPE
     SYNTAX      Unsigned32
     MAX-ACCESS  accessible-for-notify
     STATUS      current
     DESCRIPTION
        "Reversion occurs from this tunnel pair index in a tunnel group
        and is used in the definition of trap."
     ::= { wwpLeosTcePbtEncapTnlEntry 29 }   
 
 wwpLeosTcePbtEncapTnlRowStatus OBJECT-TYPE
     SYNTAX      RowStatus
     MAX-ACCESS  read-create
     STATUS      current
     DESCRIPTION
        "Setting this object to 'createAndGo' creates the entry	in the table.
	Setting this object to 'destroy' deletes the entry from the table."
     ::= { wwpLeosTcePbtEncapTnlEntry 64 }
 

 --
 -- PBT Decap tunnel table
 --

 wwpLeosTcePbtDecapTnlTable OBJECT-TYPE
     SYNTAX     SEQUENCE OF WwpLeosTcePbtDecapTnlEntry
     MAX-ACCESS not-accessible
     STATUS     current
     DESCRIPTION
            "The (conceptual) table listing the PBT decap tunnels.
             To create entry in this table use the SNMP multiple set operation.
             wwpLeosTcePbtDecapTnlName must be specified.
             wwpLeosTcePbtDecapTnlBvId must be specified.
             wwpLeosTcePbtDecapTnlPgId must be specified.
             wwpLeosTcePbtDecapTnlRowStatus must be specified."
     ::= { wwpLeosTcePbt 7 }
     
 wwpLeosTcePbtDecapTnlEntry  OBJECT-TYPE
     SYNTAX       WwpLeosTcePbtDecapTnlEntry
     MAX-ACCESS   not-accessible
     STATUS       current
     DESCRIPTION
          "An entry (conceptual row) in the wwpLeosPbtDecapTnlTable."
     INDEX {wwpLeosTcePbtDecapTnlIndex}
     ::= { wwpLeosTcePbtDecapTnlTable 1 }
     
 WwpLeosTcePbtDecapTnlEntry ::=  SEQUENCE { 
     wwpLeosTcePbtDecapTnlIndex                 Unsigned32,
     wwpLeosTcePbtDecapTnlName                  DisplayString,
     wwpLeosTcePbtDecapTnlRemoteBridgeIndex     Unsigned32,
     wwpLeosTcePbtDecapTnlRemoteBridgeName      DisplayString,
     wwpLeosTcePbtDecapTnlGroupIndex            Unsigned32,
     wwpLeosTcePbtDecapTnlGroupName             DisplayString,
     wwpLeosTcePbtDecapTnlBvId                  Unsigned32,
     wwpLeosTcePbtDecapTnlPgId                  Unsigned32,
     wwpLeosTcePbtDecapTnlPortName              DisplayString,
     wwpLeosTcePbtDecapTnlFaults                Unsigned32,
     wwpLeosTcePbtDecapTnlOperState             INTEGER,
     wwpLeosTcePbtDecapTnlFwdState              INTEGER,
     wwpLeosTcePbtDecapTnlPaired                TruthValue,
     wwpLeosTcePbtDecapTnlPairIndex             INTEGER,
     wwpLeosTcePbtDecapTnlPairOperState         INTEGER,
     wwpLeosTcePbtDecapTnlResolvedCosPolicy     INTEGER,
     wwpLeosTcePbtDecapTnlResolvedCosMapIndex   Unsigned32,
     wwpLeosTcePbtDecapTnlResolvedCosMapName    DisplayString,
     wwpLeosTcePbtDecapTnlCfmConfigured         TruthValue,
     wwpLeosTcePbtDecapTnlPairedEncapIndex      Unsigned32,
     wwpLeosTcePbtDecapTnlPairedEncapName       DisplayString,
     wwpLeosTcePbtDecapTnlStatsEnabled          TruthValue,
     wwpLeosTcePbtDecapTnlRowStatus             RowStatus
   }

 wwpLeosTcePbtDecapTnlIndex OBJECT-TYPE
     SYNTAX      Unsigned32
     MAX-ACCESS  not-accessible
     STATUS      current
     DESCRIPTION
        "This represents the unique index in the table."
     ::= { wwpLeosTcePbtDecapTnlEntry 1 }
  
 wwpLeosTcePbtDecapTnlName OBJECT-TYPE
     SYNTAX      DisplayString (SIZE (1..32))
     MAX-ACCESS  read-create
     STATUS      current
     DESCRIPTION
        "This represents the decap tunnel name. This object cannot be modified."
     ::= { wwpLeosTcePbtDecapTnlEntry 2 }
  
 wwpLeosTcePbtDecapTnlRemoteBridgeIndex OBJECT-TYPE
     SYNTAX      Unsigned32
     MAX-ACCESS  read-create 
     STATUS      current
     DESCRIPTION
        "This object represents the PBT decap tunnel remote bridge index."
     ::= { wwpLeosTcePbtDecapTnlEntry 3 }
  
 wwpLeosTcePbtDecapTnlRemoteBridgeName OBJECT-TYPE
     SYNTAX      DisplayString (SIZE (0..31))
     MAX-ACCESS  read-only
     STATUS      current
     DESCRIPTION
        "This object represents the PBT decap tunnel remote bridge name."
     ::= { wwpLeosTcePbtDecapTnlEntry 4 }
  
 wwpLeosTcePbtDecapTnlGroupIndex OBJECT-TYPE
     SYNTAX      Unsigned32
     MAX-ACCESS  read-create
     STATUS      current
     DESCRIPTION
        "This object represents the PBT decap tunnel group index."
     ::= { wwpLeosTcePbtDecapTnlEntry 5 }
  
 wwpLeosTcePbtDecapTnlGroupName OBJECT-TYPE
     SYNTAX      DisplayString (SIZE (1..31))
     MAX-ACCESS  read-only
     STATUS      current
     DESCRIPTION
        "This object represents the PBT decap tunnel group name."
     ::= { wwpLeosTcePbtDecapTnlEntry 6 }
  
 wwpLeosTcePbtDecapTnlBvId OBJECT-TYPE
     SYNTAX      Unsigned32
     MAX-ACCESS  read-create
     STATUS      current
     DESCRIPTION
        "This object represents the PBT decap tunnel BVID.
	This object cannot be modified after create."
     ::= { wwpLeosTcePbtDecapTnlEntry 7 }
  
 wwpLeosTcePbtDecapTnlPgId OBJECT-TYPE
     SYNTAX      Unsigned32
     MAX-ACCESS  read-create
     STATUS      current
     DESCRIPTION
        "This object represents the PBT decap tunnel port.
	This okbect cannot be modified after create."
     ::= { wwpLeosTcePbtDecapTnlEntry 8 }
  
 wwpLeosTcePbtDecapTnlPortName OBJECT-TYPE
     SYNTAX      DisplayString (SIZE (0..31))
     MAX-ACCESS  read-only
     STATUS      current
     DESCRIPTION
        "This object represents the PBT decap tunnel port name."
     ::= { wwpLeosTcePbtDecapTnlEntry 9 }
  

 wwpLeosTcePbtDecapTnlFaults OBJECT-TYPE
     SYNTAX      Unsigned32
     MAX-ACCESS  read-only
     STATUS      current
     DESCRIPTION
        "Each Bit Represents a fault. Value 0 represents no fault. First LSB represents port Fault. 
        Second LSB represents CFM fault and value 3 represents port and CFM fault."
     ::= { wwpLeosTcePbtDecapTnlEntry 10 }
  
 wwpLeosTcePbtDecapTnlOperState OBJECT-TYPE
     SYNTAX      INTEGER {
                     enabled(1),
                     disabled(2)
                 }
     MAX-ACCESS  read-only
     STATUS      current
     DESCRIPTION
        "This object represents the PBT decap tunnel operational state."
     ::= { wwpLeosTcePbtDecapTnlEntry 11 }
  
 wwpLeosTcePbtDecapTnlFwdState OBJECT-TYPE
     SYNTAX      INTEGER {
                    active(1),
                    standby(2)
                 }
     MAX-ACCESS  read-only
     STATUS      current
     DESCRIPTION
        "This object represents the PBT decap tunnel forwarding state."
     ::= { wwpLeosTcePbtDecapTnlEntry 12 }
  
 wwpLeosTcePbtDecapTnlPaired OBJECT-TYPE
     SYNTAX      TruthValue
     MAX-ACCESS  read-only
     STATUS      current
     DESCRIPTION
        " "
     ::= { wwpLeosTcePbtDecapTnlEntry 13 }
  
 wwpLeosTcePbtDecapTnlPairIndex OBJECT-TYPE
     SYNTAX      INTEGER (0..7)
     MAX-ACCESS  read-create
     STATUS      current
     DESCRIPTION
        "This object represents the PBT decap tunnel pair index."
     ::= { wwpLeosTcePbtDecapTnlEntry 14 }

 wwpLeosTcePbtDecapTnlPairOperState OBJECT-TYPE
     SYNTAX      INTEGER {
                     enabled(1),
                     disabled(2)
                 }
     MAX-ACCESS  read-only
     STATUS      current
     DESCRIPTION
        "This object represents the PBT decap tunnel pair operational state."
     ::= { wwpLeosTcePbtDecapTnlEntry 15 }
  
 wwpLeosTcePbtDecapTnlResolvedCosPolicy OBJECT-TYPE
     SYNTAX      INTEGER {
                        ignore(1),
                        fixed(2),
                        isidPcpMap(3)
                 }
     MAX-ACCESS  read-create
     STATUS      current
     DESCRIPTION
        "This object represents the PBT decap tunnel resolved CoS policy."
     ::= { wwpLeosTcePbtDecapTnlEntry 16 }
  
 wwpLeosTcePbtDecapTnlResolvedCosMapIndex OBJECT-TYPE
     SYNTAX      Unsigned32
     MAX-ACCESS  read-create
     STATUS      current
     DESCRIPTION
        "This object represents the PBT decap tunnel resolved CoS map index."
     ::= { wwpLeosTcePbtDecapTnlEntry 17 }
  
 wwpLeosTcePbtDecapTnlResolvedCosMapName OBJECT-TYPE
     SYNTAX      DisplayString (SIZE (0..31))
     MAX-ACCESS  read-only
     STATUS      current
     DESCRIPTION
        "This object represents the PBT decap tunnel resolved CoS map name."
     ::= { wwpLeosTcePbtDecapTnlEntry 18 }
    
 wwpLeosTcePbtDecapTnlCfmConfigured OBJECT-TYPE
     SYNTAX      TruthValue
     MAX-ACCESS  read-only
     STATUS      current
     DESCRIPTION
        "This object indicates whether the PBT decap tunnel has CFM configured. "
     ::= { wwpLeosTcePbtDecapTnlEntry 19 }
  
 wwpLeosTcePbtDecapTnlPairedEncapIndex OBJECT-TYPE
     SYNTAX      Unsigned32
     MAX-ACCESS  read-only
     STATUS      current
     DESCRIPTION
        "This object represents the PBT decap tunnel paired encap tunnel index."
     ::= { wwpLeosTcePbtDecapTnlEntry 20 }

 wwpLeosTcePbtDecapTnlPairedEncapName OBJECT-TYPE
     SYNTAX      DisplayString (SIZE (0..31))
     MAX-ACCESS  read-only
     STATUS      current
     DESCRIPTION
        "This object represents the PBT decap tunnel paired encap tunnel name."
     ::= { wwpLeosTcePbtDecapTnlEntry 21 }
  
 wwpLeosTcePbtDecapTnlStatsEnabled OBJECT-TYPE
     SYNTAX      TruthValue
     MAX-ACCESS  read-only
     STATUS      current
     DESCRIPTION
        "This object indicates whether the PBT decap tunnel has statistics enabled."
     ::= { wwpLeosTcePbtDecapTnlEntry 22 }
  
 wwpLeosTcePbtDecapTnlRowStatus OBJECT-TYPE
     SYNTAX      RowStatus
     MAX-ACCESS  read-create
     STATUS      current
     DESCRIPTION
        "Setting this object to 'createAndGo' creates the entry in the table.
	Setting this object to 'destroy' deletes the entry from the table."
     ::= { wwpLeosTcePbtDecapTnlEntry 64 }

 --
 -- PBT Service User-Frame Ingress and Egress L2 Tranform table
 --
 wwpLeosTcePbtServiceUserFrameL2TransformTable OBJECT-TYPE
     SYNTAX       SEQUENCE OF WwpLeosTcePbtServiceUserFrameL2TransformEntry
     MAX-ACCESS   not-accessible
     STATUS       current
     DESCRIPTION
	     "PBT service user frame L2 Transform table.
	 Two entries in this table are automatically
         created when a PBT service is created (one for ingress and one for egress).
         The entries are deleted from this table when the corresponding pbt service is deleted.
         Therefore, there is no rowStatus field in this table entry."
     ::= { wwpLeosTcePbt 8 }
 		
 wwpLeosTcePbtServiceUserFrameL2TransformEntry OBJECT-TYPE
     SYNTAX       WwpLeosTcePbtServiceUserFrameL2TransformEntry
     MAX-ACCESS   not-accessible
     STATUS       current
     DESCRIPTION
	     "Logical interface entry in the logical interfaces table."
     INDEX { wwpLeosTcePbtServiceIndex,
             wwpLeosTcePbtServiceUserFrameL2TransformDirection,
             wwpLeosTcePbtServiceUserFrameL2TransformTagIndex }
     ::= { wwpLeosTcePbtServiceUserFrameL2TransformTable 1 } 

 WwpLeosTcePbtServiceUserFrameL2TransformEntry ::= SEQUENCE {
     wwpLeosTcePbtServiceUserFrameL2TransformDirection      INTEGER,
     wwpLeosTcePbtServiceUserFrameL2TransformTagIndex       INTEGER,
     wwpLeosTcePbtServiceUserFrameL2TransformTagAction      INTEGER,
     wwpLeosTcePbtServiceUserFrameL2TransformTagValue       INTEGER,
     wwpLeosTcePbtServiceUserFrameL2TransformTagEtype       INTEGER,
     wwpLeosTcePbtServiceUserFrameL2TransformTagPriority    INTEGER,
     wwpLeosTcePbtServiceUserFrameL2TransformPriPolicy      INTEGER,
     wwpLeosTcePbtServiceUserFrameL2TransformUseTagValue    TruthValue,
     wwpLeosTcePbtServiceUserFrameL2TransformUseTagEtype    TruthValue
 }

 wwpLeosTcePbtServiceUserFrameL2TransformDirection OBJECT-TYPE
      SYNTAX        INTEGER  {
                        ingress(1),
                        egress(2)
                    }
      MAX-ACCESS    not-accessible
      STATUS        current
      DESCRIPTION
	      "This object specifies PBT service L2 transform direction of either 
           ingress or egress."
      ::= { wwpLeosTcePbtServiceUserFrameL2TransformEntry 1 }

 wwpLeosTcePbtServiceUserFrameL2TransformTagIndex OBJECT-TYPE
      SYNTAX        INTEGER  (1..2)
      MAX-ACCESS    not-accessible
      STATUS        current
      DESCRIPTION
	      "This object specifies pbt service user frame L2 Transform direction entry index.
                   Initial deployment supports a single tag transform.
	           As such, tag index 2 always has the tag action of none(1).
	      "
      ::= { wwpLeosTcePbtServiceUserFrameL2TransformEntry 2 }

 wwpLeosTcePbtServiceUserFrameL2TransformTagAction OBJECT-TYPE
      SYNTAX        INTEGER  {
                        none(1),
                        push(2),
                        pop(3),
                        stamp1(4),
                        stamp2(5)
                    }
      MAX-ACCESS    read-write
      STATUS        current
      DESCRIPTION
	      "This object specifies pbt service L2 Transform Action Type.
                   Initial deployment supports egress/encap actions
	           including none(1) and push(2).
                   Initial deployment supports ingress/decap actions
	           including none(1) and pop(3)."
      DEFVAL        {none}
      ::= { wwpLeosTcePbtServiceUserFrameL2TransformEntry 3 }

 wwpLeosTcePbtServiceUserFrameL2TransformTagValue OBJECT-TYPE
      SYNTAX        INTEGER  (0..4094)
      MAX-ACCESS    read-write
      STATUS        current
      DESCRIPTION
	      "This object specifies the PBT service L2 transform tag."
      DEFVAL        {0}
      ::= { wwpLeosTcePbtServiceUserFrameL2TransformEntry 4 }

 wwpLeosTcePbtServiceUserFrameL2TransformTagEtype OBJECT-TYPE
      SYNTAX        INTEGER  (0..65534)
      MAX-ACCESS    read-write
      STATUS        current
      DESCRIPTION
	      "This object specifies the L2 transform Etype.  The Etype must be specified for a push action.
         The Etype MAY be specified for a stamp action."
      DEFVAL        {0}
      ::= { wwpLeosTcePbtServiceUserFrameL2TransformEntry 5 }

 wwpLeosTcePbtServiceUserFrameL2TransformTagPriority OBJECT-TYPE
      SYNTAX        INTEGER  (0..7)
      MAX-ACCESS    read-write
      STATUS        current
      DESCRIPTION
	      "This object specifies the L2 transform tag static or fixed priority.  Use of
         this value depends on the L2 transform action, e.g., push or stamp, as well
         as the priority policy."
      DEFVAL        {0}
      ::= { wwpLeosTcePbtServiceUserFrameL2TransformEntry 6 }

 wwpLeosTcePbtServiceUserFrameL2TransformPriPolicy OBJECT-TYPE
      SYNTAX        INTEGER  {
                        leave(1),
                        static(2),
                        mapped(3)
                    }
      MAX-ACCESS    read-write
      STATUS        current
      DESCRIPTION
	      "This object specifies L2 Transform for the L2 tag priority."
      DEFVAL        {leave}
      ::= { wwpLeosTcePbtServiceUserFrameL2TransformEntry 7 }

 wwpLeosTcePbtServiceUserFrameL2TransformUseTagValue OBJECT-TYPE
      SYNTAX        TruthValue
      MAX-ACCESS    read-write
      STATUS        current
      DESCRIPTION
	      "This object specifies whether the tag value is used when stamping.  If
         the action is to push, the tag value is always used."
      DEFVAL        {false}
      ::= { wwpLeosTcePbtServiceUserFrameL2TransformEntry 8 }

 wwpLeosTcePbtServiceUserFrameL2TransformUseTagEtype OBJECT-TYPE
      SYNTAX        TruthValue
      MAX-ACCESS    read-write
      STATUS        current
      DESCRIPTION
	      "This object specifies whether to use the tag Ethertype when stamping.  If
         the action is to push, the tag Ethertype is always used."
      DEFVAL        {false}
      ::= { wwpLeosTcePbtServiceUserFrameL2TransformEntry 9 }
  
  --
  -- Notification
  --   
  wwpLeosPbtTunnelFaultNotification NOTIFICATION-TYPE
	OBJECTS	{
				wwpLeosVplsEncapTunnelId								
            }
	STATUS	deprecated
	DESCRIPTION
		"This notification is sent every time the tunnel becomes operationally down." 
	::= { wwpLeosPbtMIBNotifications 1 }                               
 
 wwpLeosPbtTunnelReversionNotification NOTIFICATION-TYPE
	OBJECTS	{
				wwpLeosVplsEncapTunnelId,
				wwpLeosVplsEncapTunnelName				
            }
	STATUS	current
	DESCRIPTION
		"This notification is sent every time backup tunnel reverts back to primary tunnel,
		once primary tunnel comes up. Var binding wwpLeosVplsEncapTunnelId represents the primary tunnel ID." 
	::= { wwpLeosPbtMIBNotifications 2 }                               

wwpLeosPbtTunnelActivateNotification NOTIFICATION-TYPE
    OBJECTS {
                wwpLeosVplsEncapTunnelId,
                wwpLeosVplsEncapTunnelName,
                wwpLeosVplsEncapTunnelId,
                wwpLeosVplsEncapTunnelName,
                wwpLeosVplsEncapTunnelActive,
                wwpLeosVplsEncapTunnelBVID
            }
    STATUS  current
    DESCRIPTION
        "This notification is sent every time tunnel is activated. Var binding wwpLeosVplsEncapTunnelId represents the tunnel ID." 
    ::= { wwpLeosPbtMIBNotifications 3 }    

    wwpLeosPbtTunnelDeactivateNotification NOTIFICATION-TYPE
    OBJECTS {
                wwpLeosVplsEncapTunnelId,
                wwpLeosVplsEncapTunnelName,
                wwpLeosVplsEncapTunnelId,
                wwpLeosVplsEncapTunnelName,
                wwpLeosVplsEncapTunnelActive,
                wwpLeosVplsEncapTunnelBVID
            }
    STATUS  current
    DESCRIPTION
        "This notification is sent every time tunnel is de-activated. Var binding wwpLeosVplsEncapTunnelId represents the tunnel ID." 
    ::= { wwpLeosPbtMIBNotifications 4 }   

  --
  -- TCE PBT Notification - add new object for notifi- only for the index
  --   

  wwpLeosTcePbtTunnelActivateNotification NOTIFICATION-TYPE
     	OBJECTS  {
                 wwpLeosTcePbtEncapTnlIndex,
                 wwpLeosTcePbtEncapTnlName,
                 wwpLeosTcePbtTnlGroupIndex,
                 wwpLeosTcePbtTnlGroupName,
                 wwpLeosTcePbtEncapTnlFwdState
                 }
    	STATUS   current
    	DESCRIPTION
       	"This notification is sent everytime tunnel of the given
        tunnel group is activated."
    ::= { wwpLeosPbtMIBNotifications 10 }                               
     

  wwpLeosTcePbtTunnelDeactivateNotification NOTIFICATION-TYPE
     	OBJECTS  {
                 wwpLeosTcePbtEncapTnlIndex,
                 wwpLeosTcePbtEncapTnlName,
                 wwpLeosTcePbtTnlGroupIndex,
                 wwpLeosTcePbtTnlGroupName,
                 wwpLeosTcePbtEncapTnlFwdState
                 }
    	STATUS   current
    	DESCRIPTION
       	"This notification is sent everytime tunnel of the given
        tunnel group is deactivated."
    ::= { wwpLeosPbtMIBNotifications 11 }                               
 
   wwpLeosTcePbtTunnelReversionNotification NOTIFICATION-TYPE
     	OBJECTS  {      
                 wwpLeosTcePbtTnlGroupIndex,
                 wwpLeosTcePbtTnlGroupName,
                 wwpLeosTcePbtEncapTnlReversionToPairIndex,
                 wwpLeosTcePbtEncapTnlReversionFromPairIndex
                 }
    	STATUS   current
    	DESCRIPTION
       	"Upon the failure of the primary tunnel, traffic is moved over to the backup 
       	 tunnel at the tunnel ingress. Tunnel reversion signifies the restoration of
       	 traffic from this backup tunnel (now active) to the primary (now standby)
       	 after the primary tunnel is restored.
       	 This notification is generated when this reversion occurs."
    ::= { wwpLeosPbtMIBNotifications 12 }                               
          
                
 --
 -- Groups definition
 --   
 pbtGlobalConfigGroup    OBJECT-GROUP
       OBJECTS { wwpLeosPbtBridgeMac, wwpLeosPbtServiceTagEType, wwpLeosPbtTunnelTagEtype, 
                 wwpLeosPbtTunnelReversionState, wwpLeosPbtTunnelReversionHoldTime, wwpLeosPbtAdminMode, wwpLeosPbtOperMode, 
                 wwpLeosPbtServiceVlanTpid }
       STATUS  current
       DESCRIPTION
               "A collection of objects providing information
               applicable global PBT confoguration."
       ::= { wwpLeosPbtMIBGroups 1 }


 pbtBridgeNameMacMapGroup    OBJECT-GROUP
       OBJECTS { wwpLeosPbtBridgeNameMacMapIndex, wwpLeosPbtBridgeNameMacMapBridgeName, wwpLeosPbtBridgeNameMacMapMacAddr, wwpLeosPbtBridgeNameMacMapUseCount, wwpLeosPbtBridgeNameMacMapRowStatus }
       STATUS  current
       DESCRIPTION
               "A collection of objects providing information
               applicable to BridgeName to MAC mapping."
       ::= { wwpLeosPbtMIBGroups 2 } 
       
 pbtReserveBvidGroup    OBJECT-GROUP
       OBJECTS { wwpLeosPbtReservedBVID, wwpLeosPbtReservedBVIDRowStatus }
       STATUS  current
       DESCRIPTION
               "A collection of objects providing information
               applicable to BVID reservation."
       ::= { wwpLeosPbtMIBGroups 3 }
 
 pbtVirtualCircuitGroup    OBJECT-GROUP
       OBJECTS { wwpLeosPbtVirtualCircuitIndex, wwpLeosPbtVirtualCircuitName, wwpLeosPbtVirtualCircuitFixedEncapTunnelId,
                 wwpLeosPbtVirtualCircuitDestBridgeIndex, wwpLeosPbtVirtualCircuitIngressISID, wwpLeosPbtVirtualCircuitEgressISID, 
                              wwpLeosPbtVirtualCircuitOperState, wwpLeosPbtVirtualCircuitEncapTunnelIdInUse, wwpLeosPbtVirtualCircuitRowStatus}
       STATUS  current
       DESCRIPTION
               "A collection of objects providing information
               applicable to PBT virtual circuit configuration."
       ::= { wwpLeosPbtMIBGroups 4 }
 
 pbtVirtualCircuitStatsGroup    OBJECT-GROUP
       OBJECTS { wwpLeosPbtVirtualCircuitTxBytesHi, wwpLeosPbtVirtualCircuitTxBytesLo, wwpLeosPbtVirtualCircuitRxBytesHi, wwpLeosPbtVirtualCircuitRxBytesLo }
       STATUS  current
       DESCRIPTION
               "A collection of objects providing information
               applicable to virtual circuit stats group."
       ::= { wwpLeosPbtMIBGroups 5 }
 
  pbtNotificationGroups NOTIFICATION-GROUP
  	   NOTIFICATIONS { wwpLeosPbtTunnelFaultNotification,
                       wwpLeosTcePbtTunnelActivateNotification,
                       wwpLeosTcePbtTunnelDeactivateNotification,
		       wwpLeosTcePbtTunnelReversionNotification}
       STATUS        current
       DESCRIPTION
            "Contains Notification supported for PBT."
       ::= { wwpLeosPbtMIBGroups 6 }
   

 --
 -- add tce group tables
 --
 --    
 END
