-- This file was included in WWP MIB release 04-21-05-0007
 --
 -- WWP-LEOS-SYSLOG-COLLECTOR-MIB.my
 --

 WWP-LEOS-SYSLOG-COLLECTOR-MIB DEFINITIONS ::= BEGIN

 IMPORTS
    IpAddress, Integer32, OBJECT-TYPE, MODULE-IDENTITY
   FROM SNMPv2-SMI
    RowStatus, TruthValue, DisplayString, TEXTUAL-CONVENTION
   FROM SNMPv2-TC
    InetAddressType,InetAddress
        FROM INET-ADDRESS-MIB
    wwpModulesLeos
   FROM WWP-SMI
   PreferredSourceAddress
       FROM CIENA-CES-MGMT-INTERFACE-MIB;

 wwpLeosSyslogCollectorMIB MODULE-IDENTITY
     LAST-UPDATED "201711150000Z"
     ORGANIZATION "Ciena Corp."
     CONTACT-INFO
        "   Mib Meister
            7035 Ridge Road
            Hanover, Maryland 21076
            USA
            Phone:  +1 800 921 1144
            Email:  support@ciena.com"

     DESCRIPTION
        "A MIB module to manage Syslog collectors on the
        LEOS based WWP and SAOS 39xx/51xx products."
     REVISION     "201711150000Z"
     DESCRIPTION
        "Updated contact info."
     REVISION    "201701130000Z"
     DESCRIPTION
       "Added support for picking the source address."
     REVISION    "201304230000Z"
     DESCRIPTION
       "Miscellaneous spelling and description corrections."
     REVISION    "201204050000Z"
     DESCRIPTION
        "Add new MIB OIDs to support IP protocol version
              independent Inet addressing.
              New attributes include: wwpLeosSyslogCollectorResolvedInetAddrType and
              wwpLeosSyslogCollectorResolvedInetAddress."
     REVISION    "200604181012Z"
     DESCRIPTION
        " Added new table wwpLeosSyslogCollectorSeverityTable to support Syslog collector severity.
          Deprecated wwpLeosSyslogCollectorMinSeverity and wwpLeosSyslogCollectorMaxSeverity.
          "
     REVISION    "200301211012Z"
     DESCRIPTION
        "Initial Creation"
     ::= { wwpModulesLeos 21 }

 
 -- -------------------------------------------------------------
 -- Textual Conventions
 -- -------------------------------------------------------------

 SyslogFacility  ::=  TEXTUAL-CONVENTION
     STATUS  current
     DESCRIPTION
         "This textual convention enumerates the facilities
         that originate Syslog messages.

         The value noMap(24) indicates that the appropriate
         facility will be provided by the individual applications
         on the managed entity.  If this option is not available
         on a particular entity attempt set the facillity to this
         value will fail with an error-status of wrongValue."
     SYNTAX  INTEGER {
                       kernel          (0), -- kernel messages
                       user            (1), -- user-level messages
                       mail            (2), -- mail system
                       daemon          (3), -- system daemons
                       auth            (4), -- authorization messages
                       syslog          (5), -- messages generated by syslogd
                       lpr             (6), -- line printer subsystem
                       news            (7), -- network news subsystem
                       uucp            (8), -- UUCP subsystem
                       cron            (9), -- clock daemon
                       authPriv        (10),-- authorization messages
                                            --    (private)
                       ftp             (11),-- ftp daemon
                       ntp             (12),-- NTP subsystem
                       security        (13),-- security subsystems
                                            --    (firewalling, etc.)
                       console         (14),-- /dev/console output
                       clockd2         (15),
                       local0          (16),
                       local1          (17),
                       local2          (18),
                       local3          (19),
                       local4          (20),
                       local5          (21),
                       local6          (22),
                       local7          (23),
                       noMap           (24)
                     }

 
 SyslogSeverity  ::=  TEXTUAL-CONVENTION
     STATUS  current
     DESCRIPTION
         "This textual convention enumerates the severity levels
          of Syslog messages.  The Syslog protocol uses the values
          0 (emergency), to 7 (debug)."
     SYNTAX  INTEGER {
                       emergency       (0),  -- system is unusable
                       alert           (1),  -- action must be taken
                                             --          immediately
                       critical        (2),  -- critical conditions
                       error           (3),  -- error conditions
                       warning         (4),  -- warning conditions
                       notice          (5),  -- normal but significant
                                             -- condition
                       info            (6),  -- informational
                       debug           (7),  -- debug-level messages
                       other           (99)  -- None of the above
                     }

 --
 -- Node definitions
 --	
 
 wwpLeosSyslogCollMIBObjects OBJECT IDENTIFIER ::= { wwpLeosSyslogCollectorMIB 1 }
 
 wwpLeosSyslogSystem  OBJECT IDENTIFIER ::= { wwpLeosSyslogCollMIBObjects 1 }
 
 wwpLeosSyslogColl    OBJECT IDENTIFIER ::= { wwpLeosSyslogCollMIBObjects 2 }
 
 -- Notifications 

 wwpLeosSyslogCollMIBNotificationPrefix  OBJECT IDENTIFIER ::= { wwpLeosSyslogCollectorMIB 2 } 
 wwpLeosSyslogCollMIBNotifications       OBJECT IDENTIFIER ::= { wwpLeosSyslogCollMIBNotificationPrefix 0 }

 -- Conformance information 
 
 wwpLeosSyslogCollMIBConformance OBJECT IDENTIFIER ::= { wwpLeosSyslogCollectorMIB 3 } 
 wwpLeosSyslogCollMIBCompliances OBJECT IDENTIFIER ::= { wwpLeosSyslogCollMIBConformance 1 } 		
 wwpLeosSyslogCollMIBGroups      OBJECT IDENTIFIER ::= { wwpLeosSyslogCollMIBConformance 2 }
 
 -- The system wide parameters

 wwpLeosSyslogEnable OBJECT-TYPE
     SYNTAX      TruthValue
     MAX-ACCESS  read-write
     STATUS      current
     DESCRIPTION
             "Specifies whether the Syslog client is enabled.
             This is the system wide parameter and it overwrites 
	     any collector specific managed object to enable
	     or disable the Syslog client."
     DEFVAL { true }
     ::= { wwpLeosSyslogSystem 1 }                                
 
wwpLeosSyslogPreferredSourceAddress OBJECT-TYPE
     SYNTAX      PreferredSourceAddress
     MAX-ACCESS  read-write
     STATUS      current
     DESCRIPTION
             "Changes the source of syslog messages to be from the default
             address or the loopback address."
     DEFVAL { default }
     ::= { wwpLeosSyslogSystem 2 }
     
 -- -------------------------------------------------------------
 -- wwpLeosSyslogCollector Table
 -- -------------------------------------------------------------
 -- Each row in this table defines a destination to which the
 -- message will be forwarded
 -- Indexed by Address and Addr Type

 wwpLeosSyslogCollectorTable OBJECT-TYPE
     SYNTAX      SEQUENCE OF WwpLeosSyslogCollectorEntry
     MAX-ACCESS  not-accessible
     STATUS      current
     DESCRIPTION
         "A table containing Syslog collector information.
	  To create entries in this table, use the SNMP multiple set
	  operation.

	  wwpLeosSyslogCollectorAddr, wwpLeosSyslogIndex and
	  wwpLeosSyslogCollectorStatus are required fields
	  that need to be set to create the entry.
	  
	  To delete an entry, set wwpLeosSyslogCollectorStatus to 'destroy'."
     ::= { wwpLeosSyslogColl 1 }

 wwpLeosSyslogCollectorEntry OBJECT-TYPE
     SYNTAX      WwpLeosSyslogCollectorEntry
     MAX-ACCESS  not-accessible
     STATUS      current
     DESCRIPTION
         "Defines the information pertaining to a Syslog collector
          to which Syslog messages are relayed.

          Entries in this table with an access level of read-
          create MUST be considered non-volatile and MUST be
	  maintained across entity resets."
     INDEX  { wwpLeosSyslogIndex }
     ::= { wwpLeosSyslogCollectorTable 1 }

 WwpLeosSyslogCollectorEntry ::=
     SEQUENCE {
         	wwpLeosSyslogIndex						Integer32,	 
         	wwpLeosSyslogCollectorAddr				DisplayString,
	 		wwpLeosSyslogCollectorResolvedAddr		IpAddress,
         	wwpLeosSyslogCollectorUDPPort			Integer32,
         	wwpLeosSyslogCollectorFacility			SyslogFacility,
         	wwpLeosSyslogCollectorMinSeverity		SyslogSeverity,
	 		wwpLeosSyslogCollectorMaxSeverity		SyslogSeverity,
	 		wwpLeosSyslogCollectorUserAdminState	INTEGER,
	 		wwpLeosSyslogCollectorDhcpAdminState	INTEGER,
	 		wwpLeosSyslogCollectorOperState			INTEGER,
         	wwpLeosSyslogCollectorStatus			RowStatus,
         	wwpLeosSyslogCollectorCustomPrefix		DisplayString,
	 	wwpLeosSyslogCollectorResolvedInetAddrType	InetAddressType,
  		wwpLeosSyslogCollectorResolvedInetAddress	InetAddress
     }

 wwpLeosSyslogIndex OBJECT-TYPE
     SYNTAX      Integer32 (1..10)
     MAX-ACCESS  not-accessible
     STATUS      current
     DESCRIPTION
           "Specifies the unique index used to represent each row in the table."
     ::= { wwpLeosSyslogCollectorEntry 1 }

 wwpLeosSyslogCollectorAddr OBJECT-TYPE
     SYNTAX      DisplayString
     MAX-ACCESS  read-create
     STATUS      current
     DESCRIPTION
           "The address for the Syslog message collector.
            It can be Host Name or IP address."
     ::= { wwpLeosSyslogCollectorEntry 2 }
 
 wwpLeosSyslogCollectorResolvedAddr OBJECT-TYPE
     SYNTAX      IpAddress
     MAX-ACCESS  read-only
     STATUS      current  
     DESCRIPTION
	     "When wwpLeosSyslogCollectorAddr represents:
          Host name    : The resolved address will either be Ipv4 address or Ipv6 address. 
          Ipv4 address : The resolved address will be the same Ipv4 address.
          Ipv6 address : The resolved address will be the same Ipv6 address.

          When the resolved address represents:
          Ipv4 address : wwpLeosSyslogCollectorResolvedAddr represents the resolved IPv4 address.
          wwpLeosSyslogCollectorResolvedInetAddr used in conjunction with wwpLeosSyslogCollectorResolvedInetAddrType
          represents the same Ipv4 address.
          Ipv6 address : wwpLeosSyslogCollectorResolvedAddr represents 0.0.0.0.
          wwpLeosSyslogCollectorResolvedInetAddr used in conjunction with wwpLeosSyslogCollectorResolvedInetAddrType
          represents the Ipv6 address."
     ::= { wwpLeosSyslogCollectorEntry 3 }
 
 wwpLeosSyslogCollectorUDPPort OBJECT-TYPE
     SYNTAX      Integer32 (1..65535)
     MAX-ACCESS  read-create
     STATUS      current
     DESCRIPTION
         "The port number on the destination to which the
          Syslog message is forwarded over the UDP
	  transport."
     DEFVAL   { 514 }
     ::= { wwpLeosSyslogCollectorEntry 4 }

 wwpLeosSyslogCollectorFacility OBJECT-TYPE
     SYNTAX      SyslogFacility
     MAX-ACCESS  read-create
     STATUS      current
     DESCRIPTION
         "The Syslog facility code that is added to the messages forwarded
          to this collector."
     DEFVAL   { daemon } 
     ::= { wwpLeosSyslogCollectorEntry 5 }

 wwpLeosSyslogCollectorMinSeverity OBJECT-TYPE
     SYNTAX      SyslogSeverity
     MAX-ACCESS  read-create
     STATUS      deprecated
     DESCRIPTION
          "Any Syslog message with a severity less than the severity
	  specified by this object is ignored by the collector.
          Note: Severity level numeric values increase as their severity
          decreases, e.g. error(3) is more severe than debug(7)."
     DEFVAL   { alert } 
     ::= { wwpLeosSyslogCollectorEntry 6 }
     
 wwpLeosSyslogCollectorMaxSeverity OBJECT-TYPE
     SYNTAX      SyslogSeverity
     MAX-ACCESS  read-create
     STATUS      deprecated
     DESCRIPTION
          "Any Syslog message with a severity greater than the severity
	  specified by this object is ignored by the collector.
          Note: Severity level numeric values increase as their severity
	  decreases, e.g. error(3) is more severe than debug(7)."
     DEFVAL   { emergency } 
     ::= { wwpLeosSyslogCollectorEntry 7 }
 
  wwpLeosSyslogCollectorUserAdminState OBJECT-TYPE
     SYNTAX      INTEGER {
			disabled(1),
			enabled(2)			
		 }
     MAX-ACCESS  read-create
     STATUS      current
     DESCRIPTION
           "Specifies the administrative state of the wwpLeosSyslogCollectorAddr 
	    configured by the user."
     ::= { wwpLeosSyslogCollectorEntry 8 }
  
 wwpLeosSyslogCollectorDhcpAdminState OBJECT-TYPE
     SYNTAX      INTEGER {
			disabled(1),
			enabled(2)			
		 }
     MAX-ACCESS  read-only
     STATUS      current
     DESCRIPTION
           "Specifies the administrative state of the wwpLeosSyslogCollectorAddr 
	    configured by DHCP."
     ::= { wwpLeosSyslogCollectorEntry 9 }

 wwpLeosSyslogCollectorOperState OBJECT-TYPE
     SYNTAX      INTEGER {
			disabled(1),
			enabled(2)			
		 }
     MAX-ACCESS  read-only
     STATUS      current
     DESCRIPTION
           "Specifies the operational state of the wwpLeosSyslogCollectorAddr."
     ::= { wwpLeosSyslogCollectorEntry 10 }

 wwpLeosSyslogCollectorStatus OBJECT-TYPE
     SYNTAX      RowStatus
     MAX-ACCESS  read-create
     STATUS      current
     DESCRIPTION
         "Used to manage the creation and deletion of the conceptual rows in this table.
          To create a row in this table, set this object to 'createAndGo'
          and specify at least wwpLeosSyslogIndex and wwpLeosSyslogCollectorAddr.
          To delete the entry set this object to 'destroy'."
     ::= { wwpLeosSyslogCollectorEntry 11 }     
  
  wwpLeosSyslogCollectorCustomPrefix OBJECT-TYPE
     SYNTAX      DisplayString(SIZE(0..15))
     MAX-ACCESS  read-create
     STATUS      current         
     DESCRIPTION
             "Specifies the Syslog custom prefix that is prepended to all Syslog messages 
              before device sends the messages to the collector."     
     DEFVAL		 {''H}
     ::= { wwpLeosSyslogCollectorEntry 12 } 
 
 wwpLeosSyslogCollectorResolvedInetAddrType OBJECT-TYPE
     SYNTAX      InetAddressType
     MAX-ACCESS  read-only
     STATUS      current
     DESCRIPTION
	     "Specifies the resolved IP address type. Used in conjunction with
              wwpLeosSyslogCollectorResolvedInetAddress.
              When set to:
              Ipv4 : wwpLeosSyslogCollectorResolvedInetAddress is compliant with
                     InetAddressIPv4
              Ipv6 : wwpLeosSyslogCollectorResolvedInetAddress is compliant with
                     InetAddressIPv6"
   
     ::= { wwpLeosSyslogCollectorEntry 13 }
 
 wwpLeosSyslogCollectorResolvedInetAddress OBJECT-TYPE
     SYNTAX      InetAddress
     MAX-ACCESS  read-only
     STATUS      current
     DESCRIPTION
           "Specifies the resolved ip address for given wwpLeosSyslogCollectorAddr.
	    If wwpLeosSyslogCollectorAddr is set to host name then
	    wwpLeosSyslogCollectorResolvedInetAddr displays the resolved IP address.
	    If wwpLeosSyslogCollectorAddr is set to IP address then
	    wwpLeosSyslogCollectorResolvedInetAddr displays the same value as the
	    wwpLeosSyslogCollectorAddr.  This OID should be used in conjuction
	    with wwpLeosSyslogCollectorResolvedInetAddrType."
     ::= { wwpLeosSyslogCollectorEntry 14 }

 -- -------------------------------------------------------------
 -- wwpLeosSyslogSeverity Table
 -- -------------------------------------------------------------
 -- Each row in this table defines a messages of this severity level that 
 -- this collector will receive
 wwpLeosSyslogCollectorSeverityTable OBJECT-TYPE
     SYNTAX      SEQUENCE OF WwpLeosSyslogCollectorSeverityEntry
     MAX-ACCESS  not-accessible
     STATUS      current
     DESCRIPTION
         "A table containing Syslog collector severity information.
	 To create entries in this table following objects must be specified.
	 -Indexes must be specified

	 To delete entry set wwpLeosSyslogCollectorStatus to destroy."
     ::= { wwpLeosSyslogColl 2 }

 wwpLeosSyslogCollectorSeverityEntry OBJECT-TYPE
     SYNTAX      WwpLeosSyslogCollectorSeverityEntry
     MAX-ACCESS  not-accessible
     STATUS      current
     DESCRIPTION
         "Defines the information pertaining to a Syslog collector severity
          to which Syslog messages are relayed. Syslog Collector
          only receives messages of severity that exist in this table."
     INDEX  { wwpLeosSyslogIndex,  wwpLeosSyslogCollectorSeverity}
     ::= { wwpLeosSyslogCollectorSeverityTable 1 }

 WwpLeosSyslogCollectorSeverityEntry ::=
     SEQUENCE {
         wwpLeosSyslogCollectorSeverity		SyslogSeverity,
	     wwpLeosSyslogCollectorSeverityRowStatus    RowStatus
     }                                    
     
 wwpLeosSyslogCollectorSeverity OBJECT-TYPE
     SYNTAX      SyslogSeverity
     MAX-ACCESS  not-accessible
     STATUS      current
     DESCRIPTION
          "This object specifies the severity of the Syslog message that this collector
           should receive."
     ::= { wwpLeosSyslogCollectorSeverityEntry 1 }  
     
 wwpLeosSyslogCollectorSeverityRowStatus OBJECT-TYPE
     SYNTAX      RowStatus
     MAX-ACCESS  read-create
     STATUS      current
     DESCRIPTION
          "Used to manage the creation and deletion of the conceptual rows in this table.
	  To create a row in this table, set this object to 'createAndGo'.
	  To delete the entry set this to 'destroy'."
     ::= { wwpLeosSyslogCollectorSeverityEntry 2 }  
    
     
  END

 --
 -- WWP-SYSLOG-COLLECTOR-MIB.my
 --
