-- This file was included in WWP MIB release 04-21-05-0007
 --
 -- WWP-LEOS-COMMUNITY-MIB.my
 -- MIB generated by MG-SOFT Visual MIB Builder Version 2.1 Build 199
 -- Sunday, March 25, 2001 at 19:17:08
 --

 WWP-LEOS-COMMUNITY-MIB DEFINITIONS ::= BEGIN

 IMPORTS 
   IpAddress, OBJECT-TYPE, MODULE-IDENTITY
       FROM SNMPv2-SMI
   RowStatus, DisplayString
       FROM SNMPv2-TC
   wwpModulesLeos
       FROM WWP-SMI;


 wwpLeosCommunityMIB MODULE-IDENTITY
       LAST-UPDATED "201711150000Z"
       ORGANIZATION "Ciena Corp."
                CONTACT-INFO
                "   Mib Meister
                    7035 Ridge Road
                    Hanover, Maryland 21076
                    USA
                    Phone:  +1 800 921 1144
                    Email:  support@ciena.com"
       DESCRIPTION
            "The MIB module for the WWP Community specific information."

       REVISION     "201711150000Z"
       DESCRIPTION
          "Updated contact info."

       REVISION    "201304230000Z"
       DESCRIPTION
            "Miscellaneous spelling and description corrections."

       REVISION    "200104031700Z"
       DESCRIPTION 
            "Initial creation."
       ::= { wwpModulesLeos 22 }

 --
 -- Node definitions
 --
	
 wwpLeosCommunityMIBObjects OBJECT IDENTIFIER ::= { wwpLeosCommunityMIB 1 }
 wwpLeosCommunity OBJECT IDENTIFIER ::= { wwpLeosCommunityMIBObjects 1 }
 

 -- Notifications 
  
 wwpLeosCommunityMIBNotificationPrefix  OBJECT IDENTIFIER ::= { wwpLeosCommunityMIB 2 } 
 wwpLeosCommunityMIBNotifications    OBJECT IDENTIFIER ::=  
                       { wwpLeosCommunityMIBNotificationPrefix 0 }

 -- Conformance information 
 
 wwpLeosCommunityMIBConformance OBJECT IDENTIFIER ::= { wwpLeosCommunityMIB 3 } 
 wwpLeosCommunityMIBCompliances OBJECT IDENTIFIER ::= { wwpLeosCommunityMIBConformance 1 } 		
 wwpLeosCommunityMIBGroups      OBJECT IDENTIFIER ::= { wwpLeosCommunityMIBConformance 2 }
		
 wwpLeosCommunityTable OBJECT-TYPE
     SYNTAX       SEQUENCE OF WwpLeosCommunityEntry
     MAX-ACCESS   not-accessible
     STATUS       deprecated
     DESCRIPTION
	     "Table of read/write Community entries. Multiple Set Operation must be used
	      to create entries in the table.
	      The following objects must be set to valid values to create entry:
	      wwpLeosCommunityRights, wwpLeosCommunityStatus.
	      If wwpLeosCommunityName is not set to anything the device sets it to public.
	      If wwpLeosCommunityAddr is not set to anything the device sets it to 0.0.0.0.
	      
	      While deleting an entry, if this is the last entry with read-only
	      or read-write permission, the device does not allow the deletion."
     ::= { wwpLeosCommunity 1 }
		
 wwpLeosCommunityEntry OBJECT-TYPE
     SYNTAX       WwpLeosCommunityEntry
     MAX-ACCESS   not-accessible
     STATUS       deprecated
     DESCRIPTION
	     "An entry for each read/write community.
	      The SNMP multiple set operation must be used
	      to create entries in the table."
     INDEX { wwpLeosCommunityIndex}
     ::= { wwpLeosCommunityTable 1 }
		 
 WwpLeosCommunityEntry ::= SEQUENCE { 
     wwpLeosCommunityIndex	     INTEGER,
     wwpLeosCommunityName            DisplayString,     
     wwpLeosCommunityAddr            DisplayString,
     wwpLeosCommunityResolvedIp	     IpAddress,
     wwpLeosCommunityRights          INTEGER,
     wwpLeosCommunityStatus          RowStatus
 }

 wwpLeosCommunityIndex OBJECT-TYPE
     SYNTAX       INTEGER (1..10)
     MAX-ACCESS   read-only
     STATUS       deprecated
     DESCRIPTION
	     "The index used in the table."
     ::= { wwpLeosCommunityEntry 1 }

 wwpLeosCommunityName OBJECT-TYPE
     SYNTAX       DisplayString
     MAX-ACCESS   read-create
     STATUS       deprecated
     DESCRIPTION
	     "The name of community string. This is a mandatory
	      object that needs to be set in order to create an entry."
     ::= { wwpLeosCommunityEntry 2 }

 wwpLeosCommunityAddr OBJECT-TYPE
    SYNTAX      DisplayString
    MAX-ACCESS  read-create
    STATUS      deprecated
    DESCRIPTION
	    "The IP Address of the host(s) or the host name with access rights.
	     A value of 0 means that access is allowed to any host.
	     This is mandatory object that needs to be set to create entry."
    ::= { wwpLeosCommunityEntry 3 }
 
 wwpLeosCommunityResolvedIp OBJECT-TYPE
    SYNTAX      IpAddress
    MAX-ACCESS  read-only
    STATUS      deprecated
    DESCRIPTION
	    "This object is set to the resolved IP address when
	     wwpLeosCommunityAddr is set to host name.
	     If wwpLeosCommunityAddr is set to IP address
	     then this object contains the same
	     IP as wwpLeosCommunityAddr."
    ::= { wwpLeosCommunityEntry 4 }

 wwpLeosCommunityRights OBJECT-TYPE
     SYNTAX       INTEGER {
                     readOnly(1),
                     readWrite(2)
                  }
     MAX-ACCESS   read-create
     STATUS       deprecated
     DESCRIPTION
	     "Rights associated with the community strings. The community Name
             associated with 'readOnly' community rights does not have any
             access (read\write) to the readWrite communities."
     ::= { wwpLeosCommunityEntry 5 }
		
 wwpLeosCommunityStatus OBJECT-TYPE
     SYNTAX      RowStatus
     MAX-ACCESS  read-create
     STATUS      deprecated
     DESCRIPTION
	     "To create a row in this table, set this object to 'createAndGo'.
	     wwpLeosCommunityRights must be valid prior to creating entry.
             The Agent should not let all the communities be deleted
             as this causes isolation of the device. At least one
             readOnly community and one readWrite community should always
             be present."
     ::= { wwpLeosCommunityEntry 6 }

 wwpLeosNotifCommunityTable OBJECT-TYPE
     SYNTAX       SEQUENCE OF WwpLeosNotifCommunityEntry
     MAX-ACCESS   not-accessible
     STATUS       deprecated
     DESCRIPTION
	     "Table of notification community entries.
	      Multiple set operation must be used
	      to create entries in the table."
     ::= { wwpLeosCommunity 2 }
		
 wwpLeosNotifCommunityEntry OBJECT-TYPE
     SYNTAX       WwpLeosNotifCommunityEntry
     MAX-ACCESS   not-accessible
     STATUS       deprecated
     DESCRIPTION
	     "An entry for each notification community.
	      Multiple set operation must be used
	      to create entries in the table."
     INDEX { wwpLeosNotifIndex }
     ::= { wwpLeosNotifCommunityTable 1 }
		 
 WwpLeosNotifCommunityEntry ::= SEQUENCE { 
     wwpLeosNotifIndex		       INTEGER,
     wwpLeosNotifCommunityName         DisplayString,     
     wwpLeosNotifCommunityDestAddr     DisplayString,
     wwpLeosNotifCommunityResolvedIpAddr IpAddress,
     wwpLeosNotifCommunityStatus       RowStatus
 }

 wwpLeosNotifIndex OBJECT-TYPE
     SYNTAX       INTEGER (1..10)
     MAX-ACCESS   read-only
     STATUS       deprecated
     DESCRIPTION
	     "The index used in the table."
     ::= { wwpLeosNotifCommunityEntry 1 }

 wwpLeosNotifCommunityName OBJECT-TYPE
     SYNTAX       DisplayString
     MAX-ACCESS   read-create
     STATUS       deprecated
     DESCRIPTION
	     "The community string to be used for the notifications.
	      This is mandatory object that needs to be set to create entry."
     ::= { wwpLeosNotifCommunityEntry 2 }

 wwpLeosNotifCommunityDestAddr OBJECT-TYPE
    SYNTAX      DisplayString
    MAX-ACCESS  read-create
    STATUS      deprecated
    DESCRIPTION
	    "The IP address or host name of the host to which notification
	     is to be sent. This is mandatory object that needs to be set to
	     create entry."
    ::= { wwpLeosNotifCommunityEntry 3 }

 wwpLeosNotifCommunityResolvedIpAddr OBJECT-TYPE
    SYNTAX      IpAddress
    MAX-ACCESS  read-only
    STATUS      deprecated
    DESCRIPTION
	    "This object is set to resolved IP address of host name
	     if wwpLeosNotifCommunityName is set to hostname.
	     If wwpLeosNotifCommunityName is set to IPv4 then
	     this object contains same IP as
	     wwpLeosNotifCommunityDestAddr."
    ::= { wwpLeosNotifCommunityEntry 4 }
		
 wwpLeosNotifCommunityStatus OBJECT-TYPE
     SYNTAX      RowStatus
     MAX-ACCESS  read-create
     STATUS      deprecated
     DESCRIPTION
	     "To create a row in this table, set this object to 'createAndGo'."
     ::= { wwpLeosNotifCommunityEntry 5 } 
                 
 END

 --
 -- WWP-COMMUNITY-MIB
 --
